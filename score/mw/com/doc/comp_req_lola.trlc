/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/

package Lola

import ScoreReq
import ScoreType

import Communication

ScoreReq.CompReq proxy_exec_less_creation {
    title = "Proxy Exception-less Creation"
    description = '''The Proxy class shall provide a non-throwing constructor using the Named Constructor idiom (See Creation of an object using *Named Constructor Approach*).
    static bmw::Result<Proxy> Proxy::Create(const Proxy::HandleType &handle) noexcept;
    Arguments:
    HandleType: The given handle parameter shall be a handle returned from one of the Proxy::FindService() API overloads.'''
    status = ScoreType.Status.valid
    security = ScoreType.Sec.yes
    safety = ScoreType.Asil.B
    reqtype = ScoreType.Reqtype.functional
    derived_from = [ Communication.time_based_arch@2 ]
    version = 2
}
