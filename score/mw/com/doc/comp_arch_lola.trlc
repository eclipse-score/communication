/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/

package LolaArch

import ScoreType
import ScoreReq
import ScoreArch

import Communication

ScoreArch.SwUnit configuration {
        title = "Lola Configuration"
        status = ScoreType.Status.valid
        security = ScoreType.Sec.yes
        safety = ScoreType.Asil.B
        satisfies = [ Communication.time_based_arch@2 ]
}
