/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package Communication

import ScoreReq

ScoreReq.AssumedSystemReq ASR_ErrorHandling {
    description = """(C++) exceptions shall not be used for error handling."""
    safety = ScoreReq.Asil.B
    rationale = "Exceptions will be directly leading to an abort and thus reducing availability of the S-CORE platform."
    version = 1
}

ScoreReq.AssumedSystemReq ASR_InterProcessCommunication {
    description = "The platform shall support inter-process communication."
    safety = ScoreReq.Asil.B
    rationale = "Application software typically consists of multiple processes which need to interact."
    version = 1
}

ScoreReq.AssumedSystemReq ASR_IntraProcessCommunication {
    description = "The platform shall support intra-process communication."
    safety = ScoreReq.Asil.B
    rationale = "Application software typically maps software building blocks into the same process."
    version = 1
}

ScoreReq.AssumedSystemReq ASR_ExternalCommunicationSomeip {
    description = "The platform shall support external communication via SOME/IP protocol."
    safety = ScoreReq.Asil.QM
    rationale = "ECU to ECU communication shall be implemented via the SOME/IP protocol."
    version = 1
}

ScoreReq.AssumedSystemReq ASR_SafeCommunication {
    description = "The platform shall support safe communication in terms of ISO 26262. I.e. it shall provide mechanisms to detect communication errors."
    safety = ScoreReq.Asil.B
    rationale = "Distributed safe systems often require communication to be safe."
    version = 1
}

ScoreReq.AssumedSystemReq ASR_SecureCommunication{
    description = "The information exchanged between applications shall be protected against unauthorized access and manipulation. The platform shall provide mechanisms to ensure confidentiality, integrity, and authenticity of the exchanged information."
    safety = ScoreReq.Asil.QM
    rationale = "Not all applications running on the platform are trusted. Therefore, applications shall not be able to manipulate or access information exchanged between other applications."
    version = 1
}

ScoreReq.AssumedSystemReq ASR_SupportForPollingBasedArchitectures {
    description = "The platform shall support a deterministic, polling-based application execution model that triggers logic based on predefined intervals."
    safety = ScoreReq.Asil.B
    rationale = "The communication middleware will provide a polling mechanism to receive new data."
    version = 1
}

ScoreReq.AssumedSystemReq ASR_SupportForDataDrivenArchitecture {
    description = "The platform shall support an event-driven application architecture where execution is triggered by data changes."
    safety = ScoreReq.Asil.QM
    rationale = "The platform shall support an event-driven architecture to allow applications to react to data changes."
    version = 1
}

ScoreReq.AssumedSystemReq ASR_SupportForRequestDrivenArchitecture {
    description = "The platform shall support a request-driven application architecture that processes requests on-demand."
    safety = ScoreReq.Asil.QM
    rationale = "Besides application, which rely on unidirectional data flow, there are applications which require a request-response communication pattern. Thus, the platform shall support a request-driven architecture to allow applications to process requests on-demand."
    version = 1
}

ScoreReq.AssumedSystemReq ASR_ProgrammingLanguagesForApplicationDevelopment {
    description = "The platform shall support implementation of applications in the following programming languages up to the ASIL-B level: C++, Rust."
    safety = ScoreReq.Asil.B
    rationale = "There are several programming languages available for safety related application development. The platform shall support communication between applications implemented in these languages."
    version = 1
}

ScoreReq.AssumedSystemReq ASR_TracingOfCommunication {
    description = "The platform shall support the tracing of communication events for internal and external communication systems."
    safety = ScoreReq.Asil.QM
    rationale = "Data and requests exchanged via the communication middleware shall be traceable to support debugging and analysis of the system."
    version = 1
}

ScoreReq.AssumedSystemReq ASR_AvailabilityOfCommunicationPartners {
    description = "The platform shall provide a mechanism to detect the availability of communication partners for internal and external communication systems and provide the required information to communicate with them."
    safety = ScoreReq.Asil.QM
    rationale = "Applications do have independent lifecycles and thus may not be available at all times. The platform shall provide a mechanism to detect the availability of communication partners and provide the required information to communicate with them."
    version = 1
}
