/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package Communication

import ScoreReq

section "com" {

    section "Public_API_Specification" {

        section "Skeleton" {

            section "Skeleton_Event" {

                /* ToDo: Potentially uncovered requirement! */
                /* broken_link_c/issue/21840363 */
                ScoreReq.CompReq SkeletonEventClass {
                    description = '''Event members within a Skeleton Class shall be of a {{SkeletonEvent}} class, whose properties are defined in this section.

                    The name and namespace of a {{SkeletonEvent}} class shall be defined by the {{mw::com}} implementation.

                    Note: It is up to the {{mw::com}} implementation, whether it defines/generates different/explicit classes for each {{SkeletonEvent}} or whether it uses a class template for {{SkeletonEvent}} class and uses the event data type (EventType) as a template argument.'''
                    safety = ScoreReq.Asil.B
                    derived_from = [Communication.FEAT_EventTypeStructure@1, Communication.FEAT_CommunicationInterfaces@1]
                    version = 1
                }

                ScoreReq.CompReq SkeletonEventClassDefinition {
                    description = '''For different event data types also different {{SkeletonEvent}}
                    {{SkeletonEvent}}

                     classes shall be defined, since the event data type influences the signature of a  class. See for example SkeletonEvent class member type EventType
                    '''
                    safety = ScoreReq.Asil.B
                    derived_from = [Communication.FEAT_EventTypeStructure@1, Communication.FEAT_ProducerConsumerPattern@1]
                    version = 1
                }

                ScoreReq.CompReq SkeletonEventCopySemantics {
                    description = '''The {{SkeletonEvent}}
                     class shall neither be copy-constructible nor copy-assignable.'''
                    safety = ScoreReq.Asil.B
                    derived_from = [Communication.FEAT_EventTypeStructure@1, Communication.FEAT_DataLoss@1]
                    version = 1
                }

                ScoreReq.CompReq SkeletonEventClassMemberTypeEventType {
                    description = '''Each {{SkeletonEvent}} class shall have a public member type {{EventType}}, which denotes the data type of an event.

                    {{{using EventType = <data type>;}}}'''
                    safety = ScoreReq.Asil.B
                    derived_from = [Communication.FEAT_EventTypeStructure@1]
                    version = 1
                }

                ScoreReq.CompReq SkeletonEventClassAllocate {
                    description = '''The {{SkeletonEvent}} class shall contain a public method:

                    {{{bmw::Result<bmw::mw::com::SampleAllocateePtr<EventType>> SkeletonEvent::Allocate() noexcept;}}}

                    Behaviour: is described in Behaviour of Allocate [ReferencedRequirements.BehaviourOfAllocate].

                    Return value: returned {{bmw::Result}} which contains

                    * on success, a {{SampleAllocateePtr}} constructed from {{EventType}} (See SampleAllocateePtr).

                    * on failure, a {{bmw::Result<void>}}, which contains a {{bmw::result::Error}}containing the value {{ComErrc::kNotOffered}} if Skeleton OfferService has not been called or the service offering has been withdrawn with a call to Skeleton StopOfferService.'''
                    safety = ScoreReq.Asil.B
                    derived_from = [Communication.FEAT_EventTypeStructure@1, Communication.FEAT_EventAccess@1, Communication.FEAT_ZeroCopy@1]
                    version = 1
                }

                ScoreReq.CompReq SkeletonEventClassSend {
                    description = '''The {{SkeletonEvent}} class shall contain a public method:

                    {{{ bmw::Result<void> SkeletonEvent::Send(const EventType &value) noexcept;}}}

                    Arguments:

                    *  value: A value of type SkeletonEvent class member type EventType which will be used according to Behaviour of Update/Send with Copy.

                    Behaviour: is described in Behaviour of Update/Send with Copy.

                    Return value: {{bmw::Result<void>}}{{bmw::result::Error}}returned  which contains a  containing the value {{ComErrc::kNotOffered}} if Skeleton OfferService has not been called or the service offering has been withdrawn with a call to Skeleton StopOfferService.'''
                    safety = ScoreReq.Asil.B
                    derived_from = [Communication.FEAT_StatelessCommunication@1]
                    version = 1
                }

                ScoreReq.CompReq SkeletonEventClassZeroCopySend {
                    description = '''The {{SkeletonEvent}} class shall contain a public method:

                    {{{bmw::Result<void> SkeletonEvent::Send(bmw::mw::com::SampleAllocateePtr<EventType> data) noexcept;}}}

                    Arguments:

                    *  data: A SampleAllocateePtr which will be used according to Behaviour of Zero-copy Update/Send.

                    Behaviour: is described in Behaviour of Zero-copy Update/Send.

                    Return value: {{bmw::Result<void>}}{{bmw::result::Error}}returned  which contains a  containing the value {{ComErrc::kNotOffered}} if Skeleton OfferService has not been called or the service offering has been withdrawn with a call to Skeleton StopOfferService'''
                    safety = ScoreReq.Asil.B
                    derived_from = [Communication.FEAT_ZeroCopy@1]
                    version = 1
                }
            }
        }
    }
}
