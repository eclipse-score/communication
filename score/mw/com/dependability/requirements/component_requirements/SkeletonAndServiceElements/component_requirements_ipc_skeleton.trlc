/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package Communication

import ScoreReq

section "com" {

    section "Public_API_Specification" {

        section "Skeleton" {

            section "Functionality" {

            /* ToDo: Potentially uncovered requirement! */
            /* broken_link_c/issue/17412229 */
            ScoreReq.CompReq SkeletonClass {
                description = '''A {{Skeleton}} class shall be based on a specific service interface definition.

                Such a class may be generated by a code generator emitting C++ code at pre-compile-time, which gets an service interface definition as input in the form of an IDL (like arxml, fidl, syml).

                Or it may be generated at compile-time based on a service interface definition in the form of a C++ type definition with the help of C++ templates, which drive the generation.

                The class name and {{namespace}} of such a {{class}} is not fixed and decided in the generation step (see above).

                Note: {{Skeleton}} is the name used for the created Skeleton in subsequent requirements.'''
                safety = ScoreReq.Asil.B
                derived_from = [Communication.FEAT_CommunicationInterfaces@1, Communication.FEAT_SupportForMultipleProgrammingLanguages@1]
                version = 1
            }

            /* ToDo: Potentially uncovered requirement! */
            /* broken_link_c/issue/22801577 */
            ScoreReq.CompReq SkeletonClassEventMembers {
                description = '''For each event the service interface definition contains, from which the Skeleton Class has been generated, it shall have a {{public}} member variable:

                * with a name equal to the name of the event in the underlying service interface definition.

                * with a type providing the features required in Skeleton Event'''
                safety = ScoreReq.Asil.B
                derived_from = [Communication.FEAT_EventTypeStructure@1, Communication.FEAT_SupportForDataDrivenArchitecture@1, Communication.FEAT_CommunicationInterfaces@1]
                version = 1
            }

            /* ToDo: Potentially uncovered requirement! */
            /* broken_link_c/issue/22801854 */
            ScoreReq.CompReq SkeletonClassFieldMembers {
                description = '''For each field the service interface definition contains, from which the Skeleton Class has been generated, it shall have a {{public}} member variable:

                * with a name equal to the name of the field in the underlying service interface definition.

                * with a type providing the features required in SkeletonField'''
                safety = ScoreReq.Asil.B
                derived_from = [Communication.FEAT_CommunicationInterfaces@1, Communication.FEAT_SupportForDataDrivenArchitecture@1]
                version = 1
            }

            /* ToDo: Potentially uncovered requirement! */
            /* broken_link_c/issue/22802065 */
            ScoreReq.CompReq SkeletonClassMethodMembers {
                description = '''For each service method the service interface definition contains, from which the Skeleton Class has been generated, it shall have a {{public}} member function:

                * with a name equal to the name of the method in the underlying service interface definition.

                * which is pure virtual

                * with return value and arguments according to: TBD'''
                safety = ScoreReq.Asil.B
                derived_from = [Communication.FEAT_SupportForRequestDrivenArchitecture@1, Communication.FEAT_MethodStructure@1, Communication.FEAT_CommunicationInterfaces@1]
                version = 1
            }

            /* ToDo: Potentially uncovered requirement! */
            /* broken_link_c/issue/21266550 */
            ScoreReq.CompReq SkeletonConstructor {
                description = '''Construction of a {{Skeleton}} instance by the user shall only be possible via one of the public static {{Create()}} methods (See Skeleton Exception-less creation with Instance Specifier and Skeleton Exception-less creation with Instance ID).

                Therefore the signature of the constructor of {{Skeleton}} is implementation defined.'''
                safety = ScoreReq.Asil.B
                derived_from = [Communication.FEAT_SupportForProgrammingLanguageIdioms@1]
                version = 1
            }

            ScoreReq.CompReq SkeletonDestructor {
                description = '''The {{Skeleton}} shall contain a public destructor.

                {{{virtual Skeleton::Skeleton() noexcept; }}}

                Behaviour: If the service provided by the skeleton is currently being offered at the time of the destruction, the offering shall be stopped.'''
                safety = ScoreReq.Asil.B
                derived_from = [Communication.FEAT_ServiceInstance@1, Communication.FEAT_SupportForProgrammingLanguageIdioms@1]
                version = 1
            }

            ScoreReq.CompReq SkeletonExceptionLessCreationWithInstanceId {
                description = '''The {{Skeleton}} class shall provide a non-throwing constructor using the Named Constructor idiom (See Creation of an object using Named Constructor approach)

                {{{static bmw::Result<Skeleton> Skeleton::Create(const mw::com::InstanceIdentifier &instance\_identifier) noexcept;

                }}}

                {{Create}} call shall fail if the service instance provided by the {{Skeleton}} is not unique (i.e., a service with the same serviceInstanceId is already created).

                Arguments:

                * instance\_identifier: For more details see [InstanceIdentifier.|ISSUE:17292144]

                * mode: This is the mode of the service implementation for processing service method invocations with {{kEvent}} as its default value. See Method Call Processing Mode for details

                Return:

                * {{Create}} call shall fail if the service instance provided by the {{Skeleton}} is not unique (i.e., a service with the same serviceInstanceId is already created). With the error code {{ComErrc::kServiceInstanceAlreadyExists}}.'''
                safety = ScoreReq.Asil.B
                derived_from = [Communication.FEAT_ErrorHandling@1]
                version = 1
            }

            ScoreReq.CompReq SkeletonExceptionLessCreationWithInstanceSpecifier {
                description = '''The {{Skeleton}} class shall provide a non-throwing constructor using the Named Constructor idiom (See Creation of an object using Named Constructor approach).

                {{{static bmw::Result<Skeleton> Skeleton::Create(const mw::com::InstanceSpecifier &instance\_specifier) noexcept;}}}

                {{Create}} call shall fail if the service instance provided by the {{Skeleton}} is not unique (i.e., a service with the same serviceInstanceId is already created).

                Arguments:

                * instance\_specifier:  For more details see [InstanceSpecifier.|ISSUE:18361210]

                * mode: This is the mode of the service implementation for processing service method invocations with {{kEvent}} as its default value. See Method Call Processing Mode for details.

                Return:

                * {{Create}} call shall fail if the service instance provided by the {{Skeleton}} is not unique (i.e., a service with the same serviceInstanceId is already created). With the error code {{ComErrc::kServiceInstanceAlreadyExists}}.'''
                safety = ScoreReq.Asil.B
                derived_from = [Communication.FEAT_ErrorHandling@1]
                version = 1
            }

            ScoreReq.CompReq SkeletonCopySemantics {
                description = '''The {{Skeleton}} class shall neither be copy-constructible nor copy-assignable.'''
                safety = ScoreReq.Asil.B
                derived_from = [Communication.FEAT_DataLoss@1]
                version = 1
            }

            ScoreReq.CompReq SkeletonMoveSemantics {
                description = '''The {{Skeleton}}
                class shall be move-constructible as well as being move-assignable.'''
                safety = ScoreReq.Asil.B
                derived_from = [Communication.FEAT_SupportForProgrammingLanguageIdioms@1, Communication.FEAT_SupportForMultipleProgrammingLanguages@1]
                version = 1
            }

            ScoreReq.CompReq SkeletonOfferService {
                description = '''The {{mw::com}}/{{LoLa}} shall provide an {{OfferService}} method as part of the {{Skeleton}} class to offer a service to applications.

                {{{bmw::Result<void> Skeleton::OfferService() noexcept;}}}

                Behaviour: is described in Behaviour of OfferService.

                Return value:

                If the {{Skeleton}} contains one or more instances of a SkeletonField class, then:

                *  if {{Update()}} has not been called yet on all of the {{SkeletonField}} instances, then the error code {{ComErrc::kFieldValueIsNotValid}} shall be returned.

                *  or, if any of the {{SkeletonField}} instances are defined with {{hasSetter=true}} and no SetHandler has been registered yet, then the errorcode {{ComErrc::kSetHandlerNotSet}} shall be returned.'''
                safety = ScoreReq.Asil.B
                derived_from = [Communication.FEAT_SupportForPollingBasedArchitecture@1, Communication.FEAT_ServiceDiscovery@1]
                version = 1
            }

            ScoreReq.CompReq SkeletonStopOfferService {
                description = '''The {{Skeleton}} shall provide a {{StopOfferService}} method:

                {{{void Skeleton::StopOfferService() noexcept;}}}

                Behaviour: is described in Behaviour of StopOfferService.'''
                safety = ScoreReq.Asil.B
                derived_from = [Communication.FEAT_SupportForPollingBasedArchitecture@1, Communication.FEAT_ServiceDiscovery@1]
                version = 1
            }
            }
        }
    }
}
