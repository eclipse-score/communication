/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package Communication

import ScoreReq

section "com" {

    section "Public_API_Specification" {

        section "Skeleton" {

            section "Functionality" {

            /* broken_link_c/issue/17412229 */
            ScoreReq.CompReq SkeletonClass {
                description = '''A {{Skeleton}} class shall be based on a specific service interface definition.

                Such a class may be generated by a code generator emitting C++ code at pre-compile-time, which gets an service interface definition as input in the form of an IDL (like arxml, fidl, syml).

                Or it may be generated at compile-time based on a service interface definition in the form of a C++ type definition with the help of C++ templates, which drive the generation.

                The class name and {{namespace}} of such a {{class}} is not fixed and decided in the generation step (see above).

                Note: {{Skeleton}} is the name used for the created Skeleton in subsequent requirements.'''
                safety = ScoreReq.Asil.B
                derived_from = [Communication.CommunicationInterfaces@1, Communication.SupportForMultipleProgrammingLanguages@1]
                version = 1
            }

            /* broken_link_c/issue/22801577 */
            ScoreReq.CompReq SkeletonClassEventMembers {
                description = '''For each event the service interface definition contains, from which the Skeleton Class has been generated, it shall have a {{public}} member variable:

                * with a name equal to the name of the event in the underlying service interface definition.

                * with a type providing the features required in Skeleton Event'''
                safety = ScoreReq.Asil.B
                derived_from = [Communication.EventType@1, Communication.SupportForDataDrivenArchitecture@1, Communication.CommunicationInterfaces@1]
                version = 1
            }

            /* broken_link_c/issue/22801854 */
            ScoreReq.CompReq SkeletonClassFieldMembers {
                description = '''For each field the service interface definition contains, from which the Skeleton Class has been generated, it shall have a {{public}} member variable:

                * with a name equal to the name of the field in the underlying service interface definition.

                * with a type providing the features required in SkeletonField'''
                safety = ScoreReq.Asil.B
                derived_from = [Communication.CommunicationInterfaces@1, Communication.SupportForDataDrivenArchitecture@1]
                version = 1
            }

            /* broken_link_c/issue/22802065 */
            ScoreReq.CompReq SkeletonClassMethodMembers {
                description = '''For each service method the service interface definition contains, from which the Skeleton Class has been generated, it shall have a {{public}} member function:

                * with a name equal to the name of the method in the underlying service interface definition.

                * which is pure virtual

                * with return value and arguments according to: TBD'''
                safety = ScoreReq.Asil.B
                derived_from = [Communication.SupportForRequestDrivenArchitecture@1, Communication.Method@1, Communication.CommunicationInterfaces@1]
                version = 1
            }

            /* broken_link_c/issue/21266550 */
            ScoreReq.CompReq SkeletonConstructor {
                description = '''Construction of a {{Skeleton}} instance by the user shall only be possible via one of the public static {{Create()}} methods (See Skeleton Exception-less creation with Instance Specifier and Skeleton Exception-less creation with Instance ID).

                Therefore the signature of the constructor of {{Skeleton}} is implementation defined.'''
                safety = ScoreReq.Asil.B
                derived_from = [Communication.SupportForProgrammingLanguageIdioms@1]
                version = 1
            }

            /* broken_link_c/issue/17432457 */
            ScoreReq.CompReq SkeletonDestructor {
                description = '''The {{Skeleton}} shall contain a public destructor.

                {{{virtual Skeleton::Skeleton() noexcept; }}}

                Behaviour: If the service provided by the skeleton is currently being offered at the time of the destruction, the offering shall be stopped.'''
                safety = ScoreReq.Asil.B
                derived_from = [Communication.ServiceInstance@1, Communication.SupportForProgrammingLanguageIdioms@1]
                version = 1
            }

            /* broken_link_c/issue/18447605 */
            ScoreReq.CompReq SkeletonExceptionLessCreationWithInstanceId {
                description = '''The {{Skeleton}} class shall provide a non-throwing constructor using the Named Constructor idiom (See Creation of an object using Named Constructor approach)

                {{{static bmw::Result<Skeleton> Skeleton::Create(const mw::com::InstanceIdentifier &instance\_identifier) noexcept;

                }}}

                {{Create}} call shall fail if the service instance provided by the {{Skeleton}} is not unique (i.e., a service with the same serviceInstanceId is already created).

                Arguments:

                * instance\_identifier: For more details see [InstanceIdentifier.|ISSUE:17292144]

                * mode: This is the mode of the service implementation for processing service method invocations with {{kEvent}} as its default value. See Method Call Processing Mode for details

                Return:

                * {{Create}} call shall fail if the service instance provided by the {{Skeleton}} is not unique (i.e., a service with the same serviceInstanceId is already created). With the error code {{ComErrc::kServiceInstanceAlreadyExists}}.'''
                safety = ScoreReq.Asil.B
                derived_from = [Communication.ErrorHandling@1]
                version = 1
            }

            /* broken_link_c/issue/17434559 */
            ScoreReq.CompReq SkeletonExceptionLessCreationWithInstanceSpecifier {
                description = '''The {{Skeleton}} class shall provide a non-throwing constructor using the Named Constructor idiom (See Creation of an object using Named Constructor approach).

                {{{static bmw::Result<Skeleton> Skeleton::Create(const mw::com::InstanceSpecifier &instance\_specifier) noexcept;}}}

                {{Create}} call shall fail if the service instance provided by the {{Skeleton}} is not unique (i.e., a service with the same serviceInstanceId is already created).

                Arguments:

                * instance\_specifier:  For more details see [InstanceSpecifier.|ISSUE:18361210]

                * mode: This is the mode of the service implementation for processing service method invocations with {{kEvent}} as its default value. See Method Call Processing Mode for details.

                Return:

                * {{Create}} call shall fail if the service instance provided by the {{Skeleton}} is not unique (i.e., a service with the same serviceInstanceId is already created). With the error code {{ComErrc::kServiceInstanceAlreadyExists}}.'''
                safety = ScoreReq.Asil.B
                derived_from = [Communication.ErrorHandling@1]
                version = 1
            }

            /* broken_link_c/issue/17432387 */
            ScoreReq.CompReq SkeletonCopySemantics {
                description = '''The {{Skeleton}} class shall neither be copy-constructible nor copy-assignable.'''
                safety = ScoreReq.Asil.B
                derived_from = [Communication.DataLoss@1]
                version = 1
            }

            /* broken_link_c/issue/17432438 */
            ScoreReq.CompReq SkeletonMoveSemantics {
                description = '''The {{Skeleton}}
                class shall be move-constructible as well as being move-assignable.'''
                safety = ScoreReq.Asil.B
                derived_from = [Communication.SupportForProgrammingLanguageIdioms@1, Communication.SupportForMultipleProgrammingLanguages@1]
                version = 1
            }

            /* broken_link_c/issue/17434118 */
            ScoreReq.CompReq SkeletonOfferService {
                description = '''The {{mw::com}}/{{LoLa}} shall provide an {{OfferService}} method as part of the {{Skeleton}} class to offer a service to applications.

                {{{bmw::Result<void> Skeleton::OfferService() noexcept;}}}

                Behaviour: is described in Behaviour of OfferService.

                Return value:

                If the {{Skeleton}} contains one or more instances of a SkeletonField class, then:

                *  if {{Update()}} has not been called yet on all of the {{SkeletonField}} instances, then the error code {{ComErrc::kFieldValueIsNotValid}} shall be returned.

                *  or, if any of the {{SkeletonField}} instances are defined with {{hasSetter=true}} and no SetHandler has been registered yet, then the errorcode {{ComErrc::kSetHandlerNotSet}} shall be returned.'''
                safety = ScoreReq.Asil.B
                derived_from = [Communication.SupportForTimeBasedArchitecture@1, Communication.ServiceDiscovery@1]
                version = 1
            }

            /* broken_link_c/issue/17434265 */
            ScoreReq.CompReq SkeletonStopOfferService {
                description = '''The {{Skeleton}} shall provide a {{StopOfferService}} method:

                {{{void Skeleton::StopOfferService() noexcept;}}}

                Behaviour: is described in Behaviour of StopOfferService.'''
                safety = ScoreReq.Asil.B
                derived_from = [Communication.SupportForTimeBasedArchitecture@1, Communication.ServiceDiscovery@1]
                version = 1
            }
            }

            section "Skeleton_Event" {

                /* broken_link_c/issue/21840363 */
                ScoreReq.CompReq SkeletonEventClass {
                    description = '''Event members within a Skeleton Class shall be of a {{SkeletonEvent}} class, whose properties are defined in this section.

                    The name and namespace of a {{SkeletonEvent}} class shall be defined by the {{mw::com}} implementation.

                    Note: It is up to the {{mw::com}} implementation, whether it defines/generates different/explicit classes for each {{SkeletonEvent}} or whether it uses a class template for {{SkeletonEvent}} class and uses the event data type (EventType) as a template argument.'''
                    safety = ScoreReq.Asil.B
                    derived_from = [Communication.EventType@1, Communication.CommunicationInterfaces@1]
                    version = 1
                }

                /* broken_link_c/issue/29235002 */
                ScoreReq.CompReq SkeletonEventClassDefinition {
                    description = '''For different event data types also different {{SkeletonEvent}}
                    {{SkeletonEvent}}

                     classes shall be defined, since the event data type influences the signature of a  class. See for example SkeletonEvent class member type EventType
                    '''
                    safety = ScoreReq.Asil.B
                    derived_from = [Communication.EventType@1, Communication.ProducerConsumerPattern@1]
                    version = 1
                }

                /* broken_link_c/issue/21840365 */
                ScoreReq.CompReq SkeletonEventCopySemantics {
                    description = '''The {{SkeletonEvent}}
                     class shall neither be copy-constructible nor copy-assignable.'''
                    safety = ScoreReq.Asil.B
                    derived_from = [Communication.EventType@1, Communication.DataLoss@1]
                    version = 1
                }

                /* broken_link_c/issue/21840366 */
                ScoreReq.CompReq SkeletonEventClassMemberTypeEventType {
                    description = '''Each {{SkeletonEvent}} class shall have a public member type {{EventType}}, which denotes the data type of an event.

                    {{{using EventType = <data type>;}}}'''
                    safety = ScoreReq.Asil.B
                    derived_from = [Communication.EventType@1]
                    version = 1
                }

                /* broken_link_c/issue/21840368 */
                ScoreReq.CompReq SkeletonEventClassAllocate {
                    description = '''The {{SkeletonEvent}} class shall contain a public method:

                    {{{bmw::Result<bmw::mw::com::SampleAllocateePtr<EventType>> SkeletonEvent::Allocate() noexcept;}}}

                    Behaviour: is described in Behaviour of Allocate [ReferencedRequirements.BehaviourOfAllocate].

                    Return value: returned {{bmw::Result}} which contains

                    * on success, a {{SampleAllocateePtr}} constructed from {{EventType}} (See SampleAllocateePtr).

                    * on failure, a {{bmw::Result<void>}}, which contains a {{bmw::result::Error}}containing the value {{ComErrc::kNotOffered}} if Skeleton OfferService has not been called or the service offering has been withdrawn with a call to Skeleton StopOfferService.'''
                    safety = ScoreReq.Asil.B
                    derived_from = [Communication.EventType@1, Communication.ZeroCopy@1]
                    version = 1
                }

                /* broken_link_c/issue/21840370 */
                ScoreReq.CompReq SkeletonEventClassSend {
                    description = '''The {{SkeletonEvent}} class shall contain a public method:

                    {{{ bmw::Result<void> SkeletonEvent::Send(const EventType &value) noexcept;}}}

                    Arguments:

                    *  value: A value of type SkeletonEvent class member type EventType which will be used according to Behaviour of Update/Send with Copy.

                    Behaviour: is described in Behaviour of Update/Send with Copy.

                    Return value: {{bmw::Result<void>}}{{bmw::result::Error}}returned  which contains a  containing the value {{ComErrc::kNotOffered}} if Skeleton OfferService has not been called or the service offering has been withdrawn with a call to Skeleton StopOfferService.'''
                    safety = ScoreReq.Asil.B
                    derived_from = [Communication.StatelessCommunication@1]
                    version = 1
                }

                /* broken_link_c/issue/21840371 */
                ScoreReq.CompReq SkeletonEventClassZeroCopySend {
                    description = '''The {{SkeletonEvent}} class shall contain a public method:

                    {{{bmw::Result<void> SkeletonEvent::Send(bmw::mw::com::SampleAllocateePtr<EventType> data) noexcept;}}}

                    Arguments:

                    *  data: A SampleAllocateePtr which will be used according to Behaviour of Zero-copy Update/Send.

                    Behaviour: is described in Behaviour of Zero-copy Update/Send.

                    Return value: {{bmw::Result<void>}}{{bmw::result::Error}}returned  which contains a  containing the value {{ComErrc::kNotOffered}} if Skeleton OfferService has not been called or the service offering has been withdrawn with a call to Skeleton StopOfferService'''
                    safety = ScoreReq.Asil.B
                    derived_from = [Communication.ZeroCopy@1]
                    version = 1
                }
            }

            section "SkeletonField" {

                section "Functionality" {

                /* broken_link_c/issue/17431949 */
                ScoreReq.CompReq SkeletonFieldClass {
                    description = '''Field members within a Skeleton Class shall be of a {{SkeletonField}} class, whose properties are defined in this section.

                    The name and namespace of a {{SkeletonField}} class shall be defined by the {{mw::com}} implementation.

                    Note: It is up to the {{mw::com}} implementation, whether it defines/generates different/explicit classes for each {{SkeletonField}} or whether it uses a class template for {{SkeletonField}} class and uses the field data type ({{FieldType}}) as a template argument.'''
                    safety = ScoreReq.Asil.B
                    derived_from = [Communication.SupportForTimeBasedArchitecture@1, Communication.CommunicationInterfaces@1]
                    version = 1
                }

                /* broken_link_c/issue/29235194 */
                ScoreReq.CompReq SkeletonFieldClassDefinition {
                    description = '''For different field data types also different {{SkeletonField}}
                    {{SkeletonField}}

                     classes shall be defined, since the field data type influences the signature of a  class. See for example SkeletonField class member type FieldType.'''
                    safety = ScoreReq.Asil.B
                    derived_from = [Communication.CommunicationInterfaces@1, Communication.ServiceInstanceNames@1]
                    version = 1
                }

                /* broken_link_c/issue/18221574 */
                ScoreReq.CompReq SkeletonFieldCopySemantics {
                    description = '''The {{SkeletonField}}
                     class shall neither be copy-constructible nor copy-assignable.'''
                    safety = ScoreReq.Asil.B
                    derived_from = [Communication.DataLoss@1]
                    version = 1
                }

                /* broken_link_c/issue/17433130 */
                ScoreReq.CompReq SkeletonFieldType {
                    description = '''Each {{SkeletonField}} class shall have a public member type {{FieldType}}, which denotes the data type of a field.

                    {{{using FieldType = <data type>;}}}'''
                    safety = ScoreReq.Asil.B
                    derived_from = [Communication.SupportForTimeBasedArchitecture@1, Communication.CommunicationInterfaces@1]
                    version = 1
                }

                /* broken_link_c/issue/17434933 */
                ScoreReq.CompReq SkeletonFieldAllocate {
                    description = '''The {{SkeletonField}} class shall contain a public method:

                    {{{bmw::Result<mw::com::SampleAllocateePtr<FieldType>> SkeletonField::Allocate() noexcept;}}}

                    Behaviour: is described in Behaviour of Allocate.

                    Return value: returned {{bmw::Result}} which contains

                    * on success, a {{SampleAllocateePtr<FieldType>}} (See SampleAllocateePtr).

                    *  on failure, a {{bmw::Result<void>}}, which contains a {{bmw::result::Error}}containing the value {{ComErrc::kNotOffered}} if Skeleton OfferService has not been called or the service offering has been withdrawn with a call to Skeleton StopOfferService.'''
                    safety = ScoreReq.Asil.B
                    derived_from = [Communication.ServiceInstance@1, Communication.ZeroCopy@1]
                    version = 1
                }

                /* broken_link_c/issue/17434775 */
                ScoreReq.CompReq SkeletonFieldClassUpdate {
                    description = '''The {{SkeletonField}} class shall contain a public method:

                    {{{ bmw::Result<void> SkeletonField::Update(const FieldType &value) noexcept;}}}

                    Arguments:

                    *  value: A value of type ProxyField Member type FieldType which will be used according to Behaviour of Update/Send with Copy.

                    Behaviour: is described in Behaviour of Update/Send with Copy and Behaviour of Setting Field Initial Value.'''
                    safety = ScoreReq.Asil.B
                    derived_from = [Communication.StatelessCommunication@1]
                    version = 1
                }

                /* broken_link_c/issue/17434778 */
                ScoreReq.CompReq SkeletonFieldClassZeroCopyUpdate {
                    description = '''The {{SkeletonField}} class shall contain a public method:

                    {{{bmw::Result<void> SkeletonField::Update(mw::com::SampleAllocateePtr<FieldType> data) noexcept;}}}

                    Arguments:

                    *  data: A SampleAllocateePtr which will be used according to Behaviour of Zero-copy Update/Send.

                    Behaviour: is described in Behaviour of Zero-copy Update/Send and Behaviour of Setting Field Initial Value'''
                    safety = ScoreReq.Asil.B
                    derived_from = [Communication.ZeroCopy@1]
                    version = 1
                }
                }
            }
        }
    }
}
