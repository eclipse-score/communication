/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package Communication

import ScoreReq

section "com" {

    section "Public_API_Specification" {

        section "Typed_Proxy" {

            section "Functionality" {

            /* broken_link_c/issue/14087509 */
            /* ToDo: Potentially uncovered requirement! */
            ScoreReq.CompReq ProxyClass {
                description = '''A {{Proxy}} class shall be based on a specific strongly typed service interface definition.

                Such a {{Proxy}} class shall either be generated by a code generator emitting C++ code at pre-compile-time, which gets a service interface definition as input in the form of an IDL (like arxml, fidl, syml).

                Or it may be generated at compile-time based on a service interface definition in the form of a C++ type definition with the help of C++ templates, which drive the generation.

                The class name and {{namespace}} of such a {{Proxy}} is not fixed and decided in the generation step (see above).

                Such a generated {{Proxy}} class then has, depending of the service interface definition it was generated from, a number of contained:

                * proxy events (0..n)

                * proxy fields (0..n)

                * proxy service methods (0..n)

                Each of these contained elements shall be represented by a public member variable.

                The name of the member variable shall be deduced from the corresponding event/field/method name of the underlying service interface definition.

                The type of the member variables is as follows:

                * event members shall be of a type providing the interface as defined in Proxy Event.

                * field members shall be of type providing the interface as defined in Proxy Field.

                * service method members shall be of type providing the interface as defined in Proxy Service Method Functionality.

                {{Proxy}}
                Note:  is the name used for the created Proxy in subsequent requirements.'''
                safety = ScoreReq.Asil.B
                derived_from = [Communication.FEAT_CommunicationInterfaces@1, Communication.FEAT_SupportForMultipleProgrammingLanguages@1]
                version = 1
            }

            /* broken_link_c/issue/14110934 */
            /* ToDo: Potentially uncovered requirement! */
            ScoreReq.CompReq ProxyConstructor {
                description = '''Construction of a {{Proxy}} instance by the user shall only be possible via the public static {{Create()}} method (See Proxy Exception-less Creation).

                Therefore the signature of the constructor of {{Proxy}} is implementation defined.'''
                safety = ScoreReq.Asil.B
                derived_from = [Communication.FEAT_SupportForProgrammingLanguageIdioms@1]
                version = 1
            }

            ScoreReq.CompReq ProxyExceptionlessCreation {
                description = '''The {{Proxy}}

                class shall provide a non-throwing constructor using the Named Constructor idiom (See Creation of an object using Named Constructor approach)

                {{{static bmw::Result<Proxy> Proxy::Create(const Proxy::HandleType &handle) noexcept;}}}

                Arguments:

                * HandleType: The given {{handle}} parameter shall be a handle returned from one of the {{Proxy::FindService()}} API overloads. See HandleType.'''
                safety = ScoreReq.Asil.B
                derived_from = [Communication.FEAT_ErrorHandling@1]
                version = 1
            }

            ScoreReq.CompReq ProxyCopySemantics {
                description = '''The {{Proxy}}
                class shall neither be copy-constructible nor copy-assignable.'''
                safety = ScoreReq.Asil.B
                derived_from = [Communication.FEAT_DataLoss@1]
                version = 1
            }

            ScoreReq.CompReq ProxyMoveSemantics {
                description = '''The {{Proxy}}
                class shall be move-constructible as well as being move-assignable.'''
                safety = ScoreReq.Asil.B
                derived_from = [Communication.FEAT_SupportForProgrammingLanguageIdioms@1, Communication.FEAT_SupportForMultipleProgrammingLanguages@1]
                version = 1
            }

            ScoreReq.CompReq ProxyFindServiceWithInstanceSpecifier {
                description = '''The {{Proxy}} class shall contain a public method:

                {{{ static bmw::Result<mw::com::ServiceHandleContainer> Proxy::FindService(mw::com::InstanceSpecifier instance\_specifier) noexcept}}}

                Arguments:

                * instance\_specifier: An instance of InstanceSpecifier Class.

                Behaviour: is described in Behaviour of FindService.

                Return values: returned bmw::Result which contains

                * on success, a HandleType for each available service instance according to Behaviour of FindService.

                *  or, a {{bmw::result::Error}} containing the value {{ComErrc::kBindingFailure}} if the lookup of all service instances corresponding to the service instance (See InstanceSpecifier Correspondence to Service Instances) by the binding returned errors.'''
                safety = ScoreReq.Asil.B
                derived_from = [Communication.FEAT_ServiceDiscovery@1]
                version = 1
            }

            ScoreReq.CompReq ProxyFindServiceWithInstanceIdentifier {
                description = '''The {{Proxy}}
                 class shall contain a public method:

                {{{static bmw::Result<mw::com::ServiceHandleContainer> Proxy::FindService(mw::com::InstanceIdentifier instance\_identifier) noexcept}}}

                Arguments:

                *  instance\_identifier: An instance of InstanceIdentifier Class.

                Behaviour: is described in Behaviour of FindService.

                Return values: returned bmw::Result which contains

                *  on success, a progress-cursor HandleType for each available service instance according to Behaviour of FindService.

                *  or, a {{bmw::result::Error}} containing the value {{ComErrc::kBindingFailure}} if the lookup of all service instances corresponding to the service instance (See InstanceIdentifier Correspondence to Service Instances) by the binding returned errors.'''
                safety = ScoreReq.Asil.B
                derived_from = [Communication.FEAT_ServiceDiscovery@1]
                version = 1
            }

            ScoreReq.CompReq ProxyStartFindServiceWithInstanceSpecifier {
                description = '''The {{Proxy}}
                 class shall contain a public method:

                {{{static bmw::Result<bmw::mw::com::FindServiceHandle> Proxy::StartFindService(bmw::mw::com::FindServiceHandler handler, bmw::mw::com::InstanceSpecifier instance\_specifier) noexcept}}}

                Arguments:

                * handler: An instance of FindServiceHandler.

                *  instance\_specifier: An instance of default-cursor InstanceSpecifier Class.

                Behaviour: is described in Behaviour of StartFindService.

                Return values: returned {{bmw::Result}} which contains

                *  on success, a FindServiceHandle for stopping the search, according to Behaviour of StartFindService.

                *  or, a {{bmw::result::Error}} containing the value {{ComErrc::kFindServiceHandlerFailure}} if the handler could not be installed.'''
                safety = ScoreReq.Asil.B
                derived_from = [Communication.FEAT_MultiBindingSupport@1]
                version = 1
            }

            ScoreReq.CompReq ProxyStartFindServiceWithInstanceIdentifier {
                description = '''The {{Proxy}}
                 class shall contain a public method:

                {{{static bmw::Result<bmw::mw::com::FindServiceHandle> Proxy::StartFindService(bmw::mw::com::FindServiceHandler handler, bmw::mw::com::InstanceIdentifier instance\_identifier) noexcept}}}

                Arguments:

                *  handler: An instance of FindServiceHandler.

                *  instance\_identifier: An instance of InstanceIdentifier Class

                Behaviour: is described in Behaviour of StartFindService.

                Return values: returned {{bmw::Result}} which contains

                *  on success, a FindServiceHandle for stopping the search, according to Behaviour of StartFindService.

                *  or, a {{bmw::result::Error}} containing the value {{ComErrc::kFindServiceHandlerFailure}} if the handler could not be installed.'''
                safety = ScoreReq.Asil.B
                derived_from = [Communication.FEAT_ServiceDiscovery@1]
                version = 1
            }

            ScoreReq.CompReq ProxyStopFindService {
                description = '''The {{Proxy}} class shall contain a public method:

                {{static bmw::Result<void> Proxy::StopFindService(bmw::mw::com::FindServiceHandle handle) noexcept}}

                Arguments:

                * {{handle}}: A handle of type FindServiceHandle identifying a previously started search.

                Behaviour: Stops the asynchronous search for available services, which has been started by either Proxy StartFindService with InstanceIdentifier or Proxy StartFindService with InstanceSpecifier. After the call has returned no further calls to the user provided FindServiceHandler takes place. Calls to {{StopFindService}} with a {{FindServiceHandle}} that was already used in a call to {{StopFindService}} which did not return an error will be silently ignored.'''
                safety = ScoreReq.Asil.B
                derived_from = [Communication.FEAT_ServiceDiscovery@1, Communication.FEAT_SafeCommunication@1]
                version = 1
            }

            ScoreReq.CompReq ProxyGetHandle {
                description = '''The {{Proxy}} class shall contain a public method:

                {{{HandleType Proxy::GetHandle() const noexcept}}}

                Return value: the handle from which the {{Proxy}} instance has been created whose type is specified in Proxy HandleType class.'''
                safety = ScoreReq.Asil.B
                derived_from = [Communication.FEAT_ServiceInstance@1]
                version = 1
            }

            ScoreReq.CompReq ProxyHandleTypeClass {
                description = '''The {{Proxy}} class shall contain a public member type {{HandleType}} which shall adhere to the .requirements of HandleType'''
                safety = ScoreReq.Asil.B
                derived_from = [Communication.FEAT_CommunicationInterfaces@1]
                version = 1
            }
            }
        }
    }
}
