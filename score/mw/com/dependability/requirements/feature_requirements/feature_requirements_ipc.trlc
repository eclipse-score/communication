/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package Communication

import ScoreReq

ScoreReq.FeatReq FEAT_SupportForPollingBasedArchitecture {
    description = "The communication framework shall provide API to support a time-based architecture."
    safety = ScoreReq.Asil.B
    derived_from = [ Communication.ASR_InterProcessCommunication@1, Communication.ASR_SupportForPollingBasedArchitectures@1, Communication.ASR_SafeCommunication@1 ]
    version = 1
}

ScoreReq.FeatReq FEAT_SupportForDataDrivenArchitecture {
    description = "The communication framework shall provide API to support a data-driven architecture."
    safety = ScoreReq.Asil.B
    derived_from = [ Communication.ASR_InterProcessCommunication@1, Communication.ASR_SupportForDataDrivenArchitecture@1 ]
    version = 1
}

ScoreReq.FeatReq FEAT_SupportForRequestDrivenArchitecture {
    description = "The communication framework shall provide API to support a request-driven architecture."
    safety = ScoreReq.Asil.B
    derived_from = [ Communication.ASR_InterProcessCommunication@1, Communication.ASR_SupportForRequestDrivenArchitecture@1 ]
    version = 1
}

ScoreReq.FeatReq FEAT_CommunicationInterfaces {
    description = "The communication framework shall support communication interfaces composed of any number of the following elements: Events, Methods, Fields, Signals."
    safety = ScoreReq.Asil.B
    derived_from = [ Communication.ASR_InterProcessCommunication@1, Communication.ASR_SupportForDataDrivenArchitecture@1, Communication.ASR_SupportForPollingBasedArchitectures@1, Communication.ASR_SafeCommunication@1, Communication.ASR_SupportForRequestDrivenArchitecture@1 ]
    version = 1
}

ScoreReq.FeatReq FEAT_EventTypeStructure {
    description = "An event-type shall be a named element of a communication interface with an associated data type."
    safety = ScoreReq.Asil.B
    derived_from = [ Communication.ASR_InterProcessCommunication@1, Communication.ASR_SupportForPollingBasedArchitectures@1 ]
    version = 1
}

ScoreReq.FeatReq FEAT_EventAccess {
    description = "An event-type shall allow its producer to assign a value and its consumers to either subscribe to value-changed events or poll unseen, cached events."
    safety = ScoreReq.Asil.B
    derived_from = [ Communication.ASR_InterProcessCommunication@1, Communication.ASR_SupportForPollingBasedArchitectures@1 ]
    version = 1
}

ScoreReq.FeatReq FEAT_MethodStructure {
    description = "A method shall be defined by a name, a specified application routine with a given set of parameters, and a return type."
    safety = ScoreReq.Asil.B
    derived_from = [ Communication.ASR_InterProcessCommunication@1, Communication.ASR_SupportForRequestDrivenArchitecture@1, Communication.ASR_SafeCommunication@1 ]
    version = 1
}

ScoreReq.FeatReq FEAT_MethodInvocation {
    description = "When a communication partner calls a method with the required parameters, the method shall invoke its application routine with those parameters, return the result to the caller, and support both synchronous and asynchronous invocation."
    safety = ScoreReq.Asil.B
    derived_from = [ Communication.ASR_InterProcessCommunication@1, Communication.ASR_SupportForRequestDrivenArchitecture@1, Communication.ASR_SafeCommunication@1 ]
    version = 1
}

ScoreReq.FeatReq FEAT_FieldTypeStructure {
    description = "A field shall be defined by a name, a data type, and dedicated getter and setter methods."
    safety = ScoreReq.Asil.B
    derived_from = [ Communication.ASR_InterProcessCommunication@1, Communication.ASR_SupportForRequestDrivenArchitecture@1, Communication.ASR_SafeCommunication@1 ]
    version = 1
}

ScoreReq.FeatReq FEAT_FieldAccess {
    description = "A field shall allow its producer to assign a value, and shall allow its consumers to subscribe to value-changed notifications, poll unseen cached values, or retrieve and update the value via its getter and setter methods."
    safety = ScoreReq.Asil.B
    derived_from = [ Communication.ASR_InterProcessCommunication@1, Communication.ASR_SupportForRequestDrivenArchitecture@1, Communication.ASR_SafeCommunication@1 ]
    version = 1
}

ScoreReq.FeatReq FEAT_SignalStructure {
    description = "A signal shall be a named element of a communication interface that does not transport data."
    safety = ScoreReq.Asil.B
    derived_from = [ Communication.ASR_InterProcessCommunication@1, Communication.ASR_SupportForRequestDrivenArchitecture@1 ]
    version = 1
}

ScoreReq.FeatReq FEAT_SignalAccess {
    description = "A signal is sent by a service-provider, and it shall be supported, that a service-consumer can wait for its reception and also check/poll if the signal was received or subscribe to update notifications."
    safety = ScoreReq.Asil.B
    derived_from = [ Communication.ASR_InterProcessCommunication@1, Communication.ASR_SupportForRequestDrivenArchitecture@1 ]
    version = 1
}

ScoreReq.FeatReq FEAT_ProducerConsumerPattern {
    description = "Communication shall be cached based on the producer-consumer pattern."
    safety = ScoreReq.Asil.B
    derived_from = [ Communication.ASR_InterProcessCommunication@1, Communication.ASR_SupportForPollingBasedArchitectures@1, Communication.ASR_SafeCommunication@1 ]
    version = 1
}

ScoreReq.FeatReq FEAT_ServiceInstance {
    description = "The communication framework shall support offering multiple service instances for the same interface."
    safety = ScoreReq.Asil.B
    derived_from = [ Communication.ASR_InterProcessCommunication@1, Communication.ASR_SafeCommunication@1 ]
    version = 1
}

ScoreReq.FeatReq FEAT_ServiceInstanceNames {
    description = "A service instance shall be offered and discoverable under one unique name."
    safety = ScoreReq.Asil.B
    derived_from = [ Communication.ASR_InterProcessCommunication@1, Communication.ASR_SafeCommunication@1 ]
    version = 1
}

ScoreReq.FeatReq FEAT_ServiceLocationTransparency {
    description = "The interface to access service instances shall be agnostic to the binding used to communicate with the service."
    safety = ScoreReq.Asil.B
    derived_from = [ Communication.ASR_InterProcessCommunication@1, Communication.ASR_SafeCommunication@1 ]
    version = 1
}

ScoreReq.FeatReq FEAT_StatelessCommunication {
    description = "The communication framework shall support stateless communication."
    safety = ScoreReq.Asil.B
    derived_from = [ Communication.ASR_InterProcessCommunication@1, Communication.ASR_SafeCommunication@1 ]
    version = 1
}

ScoreReq.FeatReq FEAT_ServiceInstanceGranularity {
    description = "The communication framework shall support multiple service instances per software architecture element."
    safety = ScoreReq.Asil.B
    derived_from = [ Communication.ASR_InterProcessCommunication@1, Communication.ASR_SafeCommunication@1 ]
    version = 1
}

ScoreReq.FeatReq FEAT_ServiceDiscovery {
    description = "The communication framework shall provide service discovery that considers version compatibility to find available services during runtime."
    safety = ScoreReq.Asil.B
    derived_from = [ Communication.ASR_InterProcessCommunication@1, Communication.ASR_SafeCommunication@1 ]
    version = 1
}

ScoreReq.FeatReq FEAT_SafeCommunication {
    description = "The communication framework shall support safe communication involving communication partners on the same or multiple criticality levels."
    safety = ScoreReq.Asil.B
    derived_from = [ Communication.ASR_InterProcessCommunication@1, Communication.ASR_SafeCommunication@1 ]
    version = 1
}

ScoreReq.FeatReq FEAT_DataCorruption {
    description = "Consumers with lower criticality shall not be able to corrupt data consumed by partners with higher criticality."
    safety = ScoreReq.Asil.B
    derived_from = [ Communication.ASR_InterProcessCommunication@1, Communication.ASR_SafeCommunication@1 ]
    version = 1
}

ScoreReq.FeatReq FEAT_DataReordering {
    description = "Consumers with lower criticality shall not be able to modify the order of data consumed by partners with higher criticality."
    safety = ScoreReq.Asil.B
    derived_from = [ Communication.ASR_InterProcessCommunication@1, Communication.ASR_SafeCommunication@1 ]
    version = 1
}

ScoreReq.FeatReq FEAT_DataRepetition {
    description = "Consumers with lower criticality shall not be able to duplicate data consumed by other communication partners with higher criticality."
    safety = ScoreReq.Asil.B
    derived_from = [ Communication.ASR_InterProcessCommunication@1, Communication.ASR_SafeCommunication@1 ]
    version = 1
}

ScoreReq.FeatReq FEAT_DataLoss {
    description = "Consumers with lower criticality shall not be able to drop data before it is consumed by partners with higher criticality."
    safety = ScoreReq.Asil.B
    derived_from = [ Communication.ASR_InterProcessCommunication@1, Communication.ASR_SafeCommunication@1 ]
    version = 1
}

ScoreReq.FeatReq FEAT_ZeroCopy {
    description = "The communication framework shall enable Zero-Copy communication without copying to-be-transferred data."
    safety = ScoreReq.Asil.B
    derived_from = [ Communication.ASR_InterProcessCommunication@1, Communication.ASR_SupportForDataDrivenArchitecture@1, Communication.ASR_SupportForRequestDrivenArchitecture@1 ]
    version = 1
}

ScoreReq.FeatReq FEAT_SupportForMultipleProgrammingLanguages {
    description = "The communication framework shall provide a public API for each supported programming language of S-CORE."
    safety = ScoreReq.Asil.B
    derived_from = [ Communication.ASR_ProgrammingLanguagesForApplicationDevelopment@1 ]
    version = 1
}

ScoreReq.FeatReq FEAT_SupportForProgrammingLanguageIdioms {
    description = "Each public API shall support the idioms of the programming language it is written in."
    safety = ScoreReq.Asil.B
    derived_from = [ Communication.ASR_ProgrammingLanguagesForApplicationDevelopment@1 ]
    version = 1
}

ScoreReq.FeatReq FEAT_UseProgrammingLanguageInfrastructure {
    description = "Each public API shall use core infrastructure of its programming language and its accompanying standard libraries."
    note = "Deviations are permitted where required and shall be commented and justified at component level."
    safety = ScoreReq.Asil.B
    derived_from = [ Communication.ASR_ProgrammingLanguagesForApplicationDevelopment@1 ]
    version = 1
}

ScoreReq.FeatReq FEAT_FullyMockablePublicAPI {
    description = "The public API shall be fully mockable."
    safety = ScoreReq.Asil.B
    derived_from = [ Communication.ASR_InterProcessCommunication@1 ]
    version = 1
}

ScoreReq.FeatReq FEAT_FakeBinding {
    description = "The communication framework shall provide a fake binding."
    safety = ScoreReq.Asil.B
    derived_from = [ Communication.ASR_InterProcessCommunication@1 ]
    version = 1
}

ScoreReq.FeatReq FEAT_MultiBindingSupport {
    description = "The communication framework shall support multiple bindings."
    safety = ScoreReq.Asil.B
    derived_from = [ Communication.ASR_InterProcessCommunication@1 ]
    version = 1
}

ScoreReq.FeatReq FEAT_BindingAgnosticPublicAPI {
    description = "The public API of the communication framework shall be binding-agnostic."
    safety = ScoreReq.Asil.B
    derived_from = [ Communication.ASR_InterProcessCommunication@1 ]
    version = 1
}

ScoreReq.FeatReq FEAT_MultiBindingDeploymentConfiguration {
    description = "The association between a service instance and its binding shall be specified in the deployment configuration."
    safety = ScoreReq.Asil.B
    derived_from = [ Communication.ASR_InterProcessCommunication@1 ]
    version = 1
}

ScoreReq.FeatReq FEAT_DeploymentConfigurationAtRuntime {
    description = "Deployment configuration shall be read from an integrity-checked configuration file at runtime."
    safety = ScoreReq.Asil.B
    derived_from = [ Communication.ASR_InterProcessCommunication@1, Communication.ASR_SafeCommunication@1 ]
    version = 1
}

ScoreReq.FeatReq FEAT_SupportForTracing {
    description = "The communication framework shall provide infrastructure to enable binding-agnostic, zero-copy, read-only tracing of communication."
    safety = ScoreReq.Asil.B
    derived_from = [ Communication.ASR_TracingOfCommunication@1, Communication.ASR_SafeCommunication@1 ]
    version = 1
}

ScoreReq.FeatReq FEAT_AccessControlListPerServiceInstance {
    description = "The communication framework shall support an Access Control List per service instance."
    safety = ScoreReq.Asil.B
    derived_from = [ Communication.ASR_InterProcessCommunication@1, Communication.ASR_SecureCommunication@1 ]
    version = 1
}

ScoreReq.FeatReq FEAT_AccessControlListForProducer {
    description = "The communication framework shall support an Access Control List for the communication partner offering a service instance (producer)."
    safety = ScoreReq.Asil.B
    derived_from = [ Communication.ASR_InterProcessCommunication@1, Communication.ASR_SecureCommunication@1 ]
    version = 1
}

ScoreReq.FeatReq FEAT_AccessControlListForConsumer {
    description = "The communication framework shall support an Access Control List for the communication partner consuming a service instance."
    safety = ScoreReq.Asil.B
    derived_from = [ Communication.ASR_InterProcessCommunication@1, Communication.ASR_SecureCommunication@1 ]
    version = 1
}

ScoreReq.FeatReq FEAT_CommunicationASILLevel {
    description = "The communication framework shall support safe communication up to ASIL-B."
    safety = ScoreReq.Asil.B
    derived_from = [ Communication.ASR_InterProcessCommunication@1, Communication.ASR_SafeCommunication@1 ]
    version = 1
}

ScoreReq.FeatReq FEAT_CommunicationPartnerCrashRecovery {
    description = "The communication framework shall support crash recovery and allow a communication partner to rejoin an earlier initialized communication after an application termination."
    safety = ScoreReq.Asil.B
    derived_from = [ Communication.ASR_InterProcessCommunication@1 ]
    version = 1
}

ScoreReq.FeatReq FEAT_CommunicationAcrossOSBoundaries {
    description = "The communication framework shall support technologies which allow communication across operating system boundaries."
    safety = ScoreReq.Asil.B
    derived_from = [ Communication.ASR_InterProcessCommunication@1 ]
    version = 1
}

ScoreReq.FeatReq FEAT_ErrorHandling {
    description = """(C++) exceptions shall not be used for error handling.
    The best way to deal with errors is to try to resolve those component internally. If not possible the caller of the function shall be notified of the error.
    For (error) returns there is a specific library to be used in S-CORE, it is the Score::Result library which is part of
    the Base Libraries feature."""
    safety = ScoreReq.Asil.B
    derived_from = [ Communication.ASR_ErrorHandling@1 ]
    version = 1
}
