/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package Communication

import ScoreReq

section "LoLa" {

    // ID: 6165713
    ScoreReq.FailureMode AnyFunctionBlocksLongerThanExpected {
        guidewords = [ ScoreReq.Guideword.DelayedFunction ]
        description = "Any API of mw::com (LoLa) blocks longer than expected (or indefinite)"
        failureeffect = "This could cause a hold of parts or the whole system."
        version = 1
        safety = ScoreReq.Asil.B
        rationale = "Our system anyhow imposes a watchdog to check for safety-related and time related paths. Thus, we do not try to safety qualify ever aspect and guarantee any execution timings."
        // potentialcause = "e.g. - Blocked mutex (e.g. dead-lock) - Wrong synchronization algorithm - endless loop - crashed services"
    }

    // ID: 6370893
    ScoreReq.FailureMode FunctionCalledFromMultipleThreads {
        guidewords = [ ScoreReq.Guideword.UnintendedFunction ]
        description = "Any API is called within multiple threads concurrently without any further synchronization."
        failureeffect = "This can lead to race-conditions which can cause data-corruption or data-loss, which could lead to a violation of any safety goal."
        version = 1
        safety = ScoreReq.Asil.B
        rationale = "Latter is covered via our AoU. If a user wants to access a proxy/skeleton from multiple threads, he shall either implement a custom synchronization, or treat it as custom instance."
        // potentialcause = "- static methods are thread-safe - API calls on different instances are thread-safe - API calls on one instance are not thread-safe."
    }

    // ID: 6370915
    ScoreReq.FailureMode MisusedApis {
        guidewords = [ ScoreReq.Guideword.ExceedingFunction ]
        description = "APIs are invoked in either an invalid context or non public APIs are invoked."
        failureeffect = "Calling non-public APIs or calling them in the wrong context can lead to un-predictable side-effects. This could cause in the worst case transmitting garbage data, which could cause a violation of any safety goal."
        version = 1
        safety = ScoreReq.Asil.B
        rationale = "Each potential cause is covered with a custom AoU."
        // potentialcause = "Potential causes are: - calling APIs of implementation namespace (aka implementation details, thus avoiding public contracts) - Invoking APIs from static context (aka static lifetime) -> can cause issues with static initialization - Using a different operating system as design for (different underlying AoUs and safety measures) - Throwing callbacks could lead to untested code-paths."
    }

    section "Runtime" {

        // ID: 6366726
        ScoreReq.FailureMode InMemoryConfigurationWrong {
            guidewords = [ ScoreReq.Guideword.LossOfFunction ]
            description = "The in-memory (cpp representation) does not match the on file-system JSON configuration."
            failureeffect = "Other functionality relies on a correct configuration. Without that, multiple functions can not operate normally which could lead to the violation of a safety goal."
            version = 1
            safety = ScoreReq.Asil.B
            rationale = "The wrong user-configuration which could cause an abnormal behavior of the mw-implementation is covered via four AoUs. The broken file is ensured via a safety-certified file system. The broken JSON is covered via a safety-certified JSON-Parser implementation. The read-in-logic to our in-memory is covered via a specific preventive measure."
            // interface = "mw.com.Runtime.Initialize"
        }
        
        ScoreReq.FailureMode InstanceSpecifierResolvesToWrongInstanceIdentifier {
            guidewords = [ ScoreReq.Guideword.UnintendedFunction ]
            description = "An InstanceSpecifier resolves to an InstanceIdentifier for a different service instance or binding than specified by the configuration."
            failureeffect = "Skeletons and proxies created from the InstanceIdentifier will correspond to the incorrect service / binding. This will result in incorrect data being transferred or being transferred in the wrong way."
            version = 1
            safety = ScoreReq.Asil.B
            rationale = ""
            interface = "score.mw.com.runtime.ResolveInstanceIDs"
        }

        ScoreReq.FailureMode InstanceSpecifierResolvesToSubsetOfInstanceIdentifier {
            guidewords = [ ScoreReq.Guideword.UnintendedFunction ]
            description = "An InstanceSpecifier resolves to a subset of InstanceIdentifiers although it should resolve to one InstanceIdentifier per supported binding."
            failureeffect = "If an InstanceSpecifier resolves to a subset of InstanceIdentifiers then not communication will not be possible across all bindings."
            version = 1
            safety = ScoreReq.Asil.B
            rationale = ""
            interface = "score.mw.com.runtime.ResolveInstanceIDs"
        }

        ScoreReq.FailureMode ResolvedInstanceIdentifierContainsWrongData {
            guidewords = [ ScoreReq.Guideword.UnintendedFunction ]
            description = "An InstanceIdentifier returned by ResolveInstanceIDs contains data that does not correctly represent the configured service instance or binding."
            failureeffect = "The corrupted data will prevent correct functioning of skeletons and proxies which will prevent finding the correct service. This will mean no communication is possible for these skeletons / proxies or they will communicate with the wrong partner."
            version = 1
            safety = ScoreReq.Asil.B
            rationale = ""
            interface = "score.mw.com.runtime.ResolveInstanceIDs"
        }

    }

    section "Service Instance Identifiers"

        section "InstanceSpecifier" {

            ScoreReq.FailureMode InstanceSpecifierCreatedWithInvalidPath {
                guidewords = [ ScoreReq.Guideword.UnintendedFunction ]
                description = "The InstanceSpecifier is created with an invalid path which does not match the required string format (i.e. shortname path)."
                failureeffect = "The InstanceSpecifier will not be able to be resolved to a valid InstanceIdentifier so no Skeletons / Proxies can be created and communication is impossible."
                version = 1
                safety = ScoreReq.Asil.B
                rationale = ""
                interface = "score.mw.com.InstanceSpecifier.Create"
            }

// Contract is that the string returned by ToString uniquely realates to the string provided to Create. i.e. different strings provided to Create will produce different strings from ToString
            ScoreReq.FailureMode ToStringCalledOnInstanceSpecifiersCreatedFromDifferentStringsReturnSameStringRepresentations {
                guidewords = [ ScoreReq.Guideword.UnintendedFunction ]
                description = "ToString returns a string which does not correctly represent the InstanceSpecifier itself."
                failureeffect = "The stringified format could be incorrect which could violate safety goals if it's used to meet a safety goal."
                version = 1
                safety = ScoreReq.Asil.B
                rationale = ""
                interface = "score.mw.com.InstanceSpecifier.ToString"
            }

      ScoreReq.FailureMode ToStringCalledOnInstanceSpecifiersCreatedFromSameStringsReturnDifferentStringRepresentations {
                guidewords = [ ScoreReq.Guideword.UnintendedFunction ]
                description = "ToString returns a string which does not correctly represent the InstanceSpecifier itself."
                failureeffect = "The stringified format could be incorrect which could violate safety goals if it's used to meet a safety goal."
                version = 1
                safety = ScoreReq.Asil.B
                rationale = ""
                interface = "score.mw.com.InstanceSpecifier.ToString"
            }
        }

        section "InstanceIdentifier" {

// contract is same 1 to 1 assurance
            ScoreReq.FailureMode ToStringCalledOnInstanceIdentifiersCreatedFromDifferentConfigurationsReturnSameStringRepresentations {
                guidewords = [ ScoreReq.Guideword.UnintendedFunction ]
                description = "ToString returns a string which does not correctly represent the InstanceIdentifier itself."
                failureeffect = "The stringified format could be incorrect which could violate safety goals if it's used to meet a safety goal."
                version = 1
                safety = ScoreReq.Asil.B
                rationale = ""
                interface = "score.mw.com.InstanceIdentifier.ToString"
            }

            ScoreReq.FailureMode ToStringCalledOnInstanceIdentifiersCreatedFromSameConfigurationsReturnDifferentStringRepresentations {
                guidewords = [ ScoreReq.Guideword.UnintendedFunction ]
                description = "ToString returns a string which does not correctly represent the InstanceIdentifier itself."
                failureeffect = "The stringified format could be incorrect which could violate safety goals if it's used to meet a safety goal."
                version = 1
                safety = ScoreReq.Asil.B
                rationale = ""
                interface = "score.mw.com.InstanceIdentifier.ToString"
            }

        }

    }

    section "Skeleton" {

        section "Creation" {

            // ID: 6165662
            ScoreReq.FailureMode CreationOfSkeletonNotPossible {
                guidewords = [ ScoreReq.Guideword.LossOfFunction ]
                description = "It is not possible to create a skeleton instance"
                failureeffect = "No communication possible."
                version = 1
                safety = ScoreReq.Asil.B
                rationale = "We added an AoU that no Safety-goal shall be harmed, if a service is not offered. Thus, this failure cannot have any safety-related bad effect."
                // interface = "mw.com.Skeleton.Create"
            }

            ScoreReq.FailureMode CreatingAlreadyCreatedService {
                guidewords = [ ScoreReq.Guideword.UnintendedFunction ]
                description = "A skeleton is created for a service for which there is already a succesfully created skeleton."
                failureeffect = "If the duplicate skeleton were to be offered, the existing communication could break up. Or data could be overwritten while transmitted. In any case this could cause potential garbage data, which could cause a complete malfunction of the system."
                version = 1
                safety = ScoreReq.Asil.B
                rationale = ""
                interface = "mw.com.Skeleton.Create"
            }


            ' SkeletonEventCannotBeCreated - event name in c++ interface is in configuration

            ' SkeletonFieldCannotBeCreated

            ' SkeletonMethodCannotBeCreated
        }

        // Note. IsAvailableToConsumers means that if the proxy does everything correctly on its side, the service can be found. It doesn't consider issues in proxy side service discovery (i.e. in FindService or StartFindService).
        section "OfferAService" {

            ScoreReq.FailureMode OfferServiceFailedButServiceCanBeFoundToConsumers {
                guidewords = [ ScoreReq.Guideword.LossOfFunction ]
                description = "OfferService failed but the service is still visible to proxies and can be found via service discovery."
                failureeffect = "A proxy which has been created after finding a service expects that it can communicate with / receive data from the connected skeleton. If the service was not succesfully offered, but the proxy finds it anyway, the proxy communication semantics are affected and thus can affect any safety goal."
                version = 1
                safety = ScoreReq.Asil.B
                rationale = "By explicitly requesting this case in our requirements and testing the requirement we make sure that the error case is tackled. The not working update functionality is covered already by other FMEA elements in Section SendAnEventOrField"
                interface = "mw.com.Skeleton.OfferService"
            }

            ScoreReq.FailureMode OfferServiceSucceededWithoutInitialFieldValue {
                guidewords = [ ScoreReq.Guideword.LossOfFunction ]
                description = "A service is offered, although at least one of its field has no initial value set by the provider."
                failureeffect = "A user expects after seeing a service offered, in a call to GetNewSamples(), that he would at least get one new sample. This could hinder the expected semantics on user side, and thus affect any safety goal."
                version = 1
                safety = ScoreReq.Asil.B
                rationale = "By explicitly requesting this case in our requirements and testing the requirement we make sure that the error case is tackled. The not working update functionality is covered already by other FMEA elements in Section SendAnEventOrField"
                // interface = "mw.com.Skeleton.OfferService"
            }

            ScoreReq.FailureMode OfferServiceSucceededButServiceCannotBeFoundByConsumers {
                guidewords = [ ScoreReq.Guideword.LossOfFunction ]
                description = "A skeleton service is offering a service, but the service is silently not offered."
                failureeffect = "A proxy cannot be created so no communication will happen, thus no information can be exchanged, thus any overall system functionality can stop."
                version = 1
                safety = ScoreReq.Asil.B
                rationale = "We added an AoU that no Safety-goal shall be harmed, if a service is not offered. Thus, this failure cannot have any safety-related bad effect."
                // interface = "mw.com.Skeleton.OfferService"
            }

            ScoreReq.FailureMode OfferServiceSucceededButServiceIsOnlyAvailableToSubsetOfConsumers {
                guidewords = [ ScoreReq.Guideword.PartialFunction ]
                description = "A skeleton offers a service, which is not visible to all consumers, but only to a subset of them."
                failureeffect = "This is equal to the case OfferServiceSucceededButServiceIsNotAvailableToConsumers, thus for the consumers which cannot find the service no information can be exchanged, thus any overall system functionality can stop."
                version = 1
                safety = ScoreReq.Asil.B
                rationale = "Since both sub-trees (config is wrong, no ASIL level) are captured via different fault trees, we only need to ensure that all events are actually always registered. This is ensured via an preventive measure."
                // interface = "mw.com.Skeleton.OfferService"
            }
        }

        section "StopOfferAService" {
            ScoreReq.FailureMode StopOfferNotStoppedInSD {
                guidewords = [ ScoreReq.Guideword.UnintendedFunction ]
                description = "A service instance was offered via service discovery, but it wasn't withdrawn from service discovery in the stop offer."
                failureeffect = "Either a service is found by a consumer, even though it shall no longer be found or an event/field subscription state stays in SUBSCRIBED although it isn't."
                version = 1
                safety = ScoreReq.Asil.B
                rationale = "Consumers might expect, that they will still get event or field data updates, although they won't happen. They also might expect, they can successfully call a method, which they can't."
            }

            ScoreReq.FailureMode StopOfferWrongInstanceStoppedInSD {
                 guidewords = [ ScoreReq.Guideword.UnintendedFunction, ScoreReq.Guideword.LossOfFunction ]
                 description = "Same as in StopOfferNotStoppedInSD. Additionally another service instance, which is still being offered, is withdrawn from service discovery."
                 failureeffect = "Same as in StopOfferNotStoppedInSD. In addition: Consumers using this service instance will not be able to find it anymore or would see subscription state changes of subscribed events/fields from SUBSCRIBED to SUBSCRIPTION_PENDING."
                 version = 1
                 safety = ScoreReq.Asil.B
                 rationale = "Same as in StopOfferNotStoppedInSD. In addition: Other consumers might falsely deduce, that they won't receive any new data from the service instance"
            }

            ScoreReq.FailureMode StopOfferUnlinkWrongSHMObjects {
                 guidewords = [ ScoreReq.Guideword.LossOfFunction ]
                 description = "Skeleton instance did unlink shared memory objects which do not belong to the service instance being stop offered."
                 failureeffect = "Consumers finding the service instance of which the shared memory objects have been falsely unlinked, will fail to create a proxy instance and thus will not be able to communicate with the service instance."
                 version = 1
                 safety = ScoreReq.Asil.B
                 rationale = "From the consumer's point of view, this is an unexpected failure when creating a proxy instance from a handle, eventually leading to a termination."
            }

            ScoreReq.FailureMode StopOfferInconsistent {
                 guidewords = [ ScoreReq.Guideword.LossOfFunction, ScoreReq.Guideword.UnintendedFunction ]
                 description = "Skeleton instance is in an inconsistent state after stop offering: Either the stop offer was not forwarded to the binding or failed at the binding. Or it wasn't forwarded to the dependent service elements or their bindings or failed at them."
                 failureeffect = "The stop offer is incomplete and thus incoming service method calls may be still dispatched to handlers. Or doing a later StartOfferService may fail because the skeleton instance is in an inconsistent state."
                 version = 1
                 safety = ScoreReq.Asil.B
                 rationale = "The user might see unexpected errors from later calls to StartOfferService. The user might see unexpected calls to his service method handlers."
            }
        }

        section "AllocateAnEventOrField" {

            // ID: 6164265
            ScoreReq.FailureMode MemoryAllocatedInWrongSection {
                guidewords = [ ScoreReq.Guideword.UnintendedFunction ]
                description = "The memory for an event is allocated in the wrong memory section (e.g. in Heap, another Shared Memory segment or the stack)."
                failureeffect = "This could cause transmitting garbage data between processes, causing a complete outage of the system. In the worst case the safety goal could be violated."
                version = 1
                safety = ScoreReq.Asil.B
                rationale = "Any user faults are covered by the AoU, that no user provided types shall be used with the mw::com. The following faults * \"Middleware provided type is wrong\" * \"Shared memory resource not forwarded\" * \"Shared Memory Factory returns wrong memory resource\" * \"Shared Memory resource returns wrong proxy\" * \"Forwarded wrong shared memory segment from the beginning\" * \"Shared Memory Resource opens wrong shared memory segment\" * Stack allocations are prevented by ensure correct working functionality assigned by single requirements. ProxyID overwritten is the most critical part, which needs another safety mechanism. An accidentally overwrite will be covered by additional checks (e.g. CRC). An OffsetPTR corruption would be covered by our active bound checking, so this is no new issue that could occur."
            }

            // ID: 6164791
            ScoreReq.FailureMode TooFewMemoryAllocated {
                guidewords = [ ScoreReq.Guideword.PartialFunction ]
                description = "The event allocation allocates too few memory (including no memory at all)."
                failureeffect = "This could cause transmitting garbage data between processes, causing a complete outage of the system. In the worst case the safety goal could be violated."
                version = 1
                safety = ScoreReq.Asil.B
                rationale = "1. \"Literally wrong number of slots reserved\": Covered by preventive measure \"reserve configured number of slots\" 2. \"More than one SampleAllocateePtr in parallel\": Covered by AoUs (\"one producer, one allocatee ptr\", \"no-copy on send, while holding allocatee ptr\", since copy-send calls allocate implicitly) 3. \"Holds more sample ptr than announced\": Covered by \"a proxy instance shall not retrieve more sample ptr...\" 4. \"Holds more sample ptr than configured\": Covered by AoUs (\"configured maximum number of subscriber\", \" configured maximum number of elements\") 5. \"slot allocation logic broken\": Covered by \"Slot allocation synchronisation\" 6. \"Mapping of wrong EventId\": Covered by \"EventFqId shall be constructed from the associated configuration values\" 7. \"Shared memory truncation fails\": Is controlled by \" A process shall terminate, if the truncation of a shared memory segment fails.\" by transitioning into a safe state. 8. The necessary size calculation cannot fail, since it is just a sizeof() 9. \"Allocate claims to few memory\": Is covered by \"SharedMemoryResource shall allocate the requested memory on an allocate call\" Note: A Proxy can either be a \"regular\" proxy, or an \"ipc tracing\" proxy."
                // interface = "mw.com.Event.Allocate"
            }

            // ID: 6164809
            ScoreReq.FailureMode WronglyAlignedMemoryAllocated {
                guidewords = [ ScoreReq.Guideword.UnintendedFunction ]
                description = "The memory for an event/field is allocated in a wrongly aligned manner."
                failureeffect = "This could cause transmitting garbage data between processes, causing a complete outage of the system. In the worst case the safety goal could be violated."
                version = 1
                safety = ScoreReq.Asil.B
                rationale = "We ensure with our preventive measure that wrong alignment could happen."
                // interface = "score.mw.com.SkeletonEvent.Allocate"
            }

            // ID: 6164821
            ScoreReq.FailureMode TooMuchMemoryAllocated {
                guidewords = [ ScoreReq.Guideword.ExceedingFunction ]
                description = "There is too much memory allocated for one event/field"
                failureeffect = "While to much memory has no immediate bad effect, this could cause an overall resource exhaustion within the system."
                version = 1
                safety = ScoreReq.Asil.B
                rationale = "Basically the same faults and reactions as on [ISSUE:Failuremode TooFewMemoryAllocated] apply. There is no benefit to duplicate all the information also within this fault"
                // potentialcause = "The possible causes are the same as [ISSUE:Failuremode TooFewMemoryAllocated]"
            }

            // ID: 6164832
            ScoreReq.FailureMode AllocatesAlreadyAllocatedMemory {
                guidewords = [ ScoreReq.Guideword.UnintendedFunction ]
                description = "The memory for an event/field is allocated from already allocated memory (not free memory)."
                failureeffect = "This could cause transmitting garbage data between processes, causing a complete outage of the system. In the worst case the safety goal could be violated."
                version = 1
                safety = ScoreReq.Asil.B
                rationale = "Our preventive measure ensure that the allocation within a Shared Memory Resource works as expected."
                // potentialcause = "The only possibility is a mistake in the allocation strategy of a Shared Memory Resource."
            }
        }

        section "SendAnEventOrField" {

            // ID: 6164966
            ScoreReq.FailureMode SendingEventChangesUserData {
                guidewords = [ ScoreReq.Guideword.UnintendedFunction ]
                description = "A call to send manipulates the data that was provided by the caller."
                failureeffect = "This could cause transmitting garbage data between processes, causing a complete outage of the system. In the worst case the safety goal could be violated."
                version = 1
                safety = ScoreReq.Asil.B
                rationale = "Most of the possible errors have been discussed with [ISSUE:Failuremode TooFewMemoryAllocated]. The issue with the generic trace API is covered by its custom preventive measure. Only the direct manipulation is a net yet covered possible fault cause. Which is addressed with our preventive measure."
                // interface = "mw.com.Event.Send"
            }

            // ID: 6164982
            ScoreReq.FailureMode SendingAnEventOrFieldSendsDataOnlyPartially {
                guidewords = [ ScoreReq.Guideword.PartialFunction ]
                description = "Data that is send by the user, only reaches partially the consumer. This can happen in two ways, only a partial number of consumers see the data or all consumers see only partial data."
                failureeffect = "This could cause transmitting garbage data between processes, causing a complete outage of the system. In the worst case the safety goal could be violated."
                version = 1
                safety = ScoreReq.Asil.B
                rationale = "issue not possible with current design. no additional measures required."
                // interface = "mw.com.Event.Send"
            }

            // ID: 6164996
            ScoreReq.FailureMode SendingEventOnlyPartiallyNotifiesConsumer {
                guidewords = [ ScoreReq.Guideword.PartialFunction ]
                description = "When data is sent, consumers that have a callback registered, are only partially notified."
                failureeffect = "This could cause that data is not processed, causing a complete outage of the system. In the worst case the safety goal could be violated."
                version = 1
                safety = ScoreReq.Asil.B
                rationale = "Our AoU states that the fault shall not cause safety goal violations. Thus, no additional measures are required."
                // interface = "mw.com.Event.Send"
            }

            // ID: 6165326
            ScoreReq.FailureMode SendingEventSendsToWrongConsumer {
                guidewords = [ ScoreReq.Guideword.UnintendedFunction ]
                description = "An event or field is sent to the wrong consumer."
                failureeffect = "This could cause transmitting garbage data between processes, causing a complete outage of the system. In the worst case the safety goal could be violated."
                version = 1
                safety = ScoreReq.Asil.B
                rationale = "All possible fault causes are already addressed with [ISSUE:Failuremode TooFewMemoryAllocated]"
                // interface = "mw.com.Event.Send"
            }

            // ID: 6165344
            ScoreReq.FailureMode SendingAnEventOrFieldSendsSameSampleNtimes {
                guidewords = [ ScoreReq.Guideword.ExceedingFunction ]
                description = "Instead of sending a sample (one data point) only once, it is send multiple times."
                failureeffect = "This could cause transmitting garbage data between processes, causing a complete outage of the system. In the worst case the safety goal could be violated."
                version = 1
                safety = ScoreReq.Asil.B
                rationale = "The only possible fault cause is eliminated with our preventive measure."
                // interface = "mw.com.Event.Send"
            }

            // ID: 6165624
            ScoreReq.FailureMode SendingEventDoesNotFreeResources {
                guidewords = [ ScoreReq.Guideword.PartialFunction ]
                description = "Resources in the middleware that have been allocated with a previous allocation, are not freed after returning from send/update."
                failureeffect = "This could lead to a resource exhaustion of the system. Leading to a situation where no communication would be possible."
                version = 1
                safety = ScoreReq.Asil.B
                rationale = "All three steps that could fail during freeing the resources are prevented by their respective requirements."
                // interface = "mw.com.Event.Send"
            }
        }

        section "Destruction" {

            // ID: 6165759
            ScoreReq.FailureMode WrongResourcesFreed {
                guidewords = [ ScoreReq.Guideword.UnintendedFunction ]
                description = "A destruction of one skeleton instances, frees the resources of another skeleton instance."
                failureeffect = "This could cause transmitting garbage data between processes, causing a complete outage of the system. In the worst case the safety goal could be violated."
                version = 1
                safety = ScoreReq.Asil.B
                rationale = "A wrong freeing of resources would only be possible by a wrong holding of resources, which is avoided by our two preventive measures."
                // interface = "mw.com.Skeleton.Destroy"
            }

            // ID: 6165782
            ScoreReq.FailureMode NoResourcesFreed {
                guidewords = [ ScoreReq.Guideword.LossOfFunction ]
                description = "The resources allocated on construction and during operation are not freed on destruction."
                failureeffect = "Can cause an overall resource exhaustion."
                version = 1
                safety = ScoreReq.Asil.B
                rationale = "Another safety argument is added that shall avoid that no resources are freed."
                // interface = "mw.com.Skeleton.Destroy"
            }

            // ID: 6165797
            ScoreReq.FailureMode EarlyCleanUp {
                guidewords = [ ScoreReq.Guideword.ExceedingFunction ]
                description = "Resources are freed while still being used."
                failureeffect = "This could cause transmitting garbage data between processes, causing a complete outage of the system. In the worst case the safety goal could be violated."
                version = 1
                safety = ScoreReq.Asil.B
                rationale = "By only freeing resources on destruction, we can avoid early resource clean ups."
                // interface = "mw.com.Skeleton.Destroy"
            }
        }
        section "Handle Method Calls" {

            // Fault-Tree $FailureMode [Communication.WrongInArgsUsed]
            // Reference as mitigation measures:
            // - Callee used InArgs in wrong layout: Mitigated by AoU ScoreReq.AoU SameCompilerSettingsForProviderAndConsumerSide
            // - Callee used InArgs while concurrently updated: Mitigated by AoU ScoreReq.AoU ValidityOfPointerOnLoLaPointer. ToDo: extend this AoU for MethodElementPtrs!
            // Reference as prevention measures:
            // - Callee used InArgs from wrong location: ToDo: Requirement, that we make sure, that the provided MethodInArgPtrs are actually pointing to the right location.
            // - Callee used InArgs before being provided: ToDo: Requirement, that we make sure, that the user handler is only called, when the provided in-arg references are pointing to completely setup in-arg.
            // - InArgs corrupted by 3d party: ToDo: Requirement: shm-objects created for method calls need to be accessible only to service provider instance and the proxy instance.
            ScoreReq.FailureMode WrongMethodInArgsUsed {
                guidewords = [ ScoreReq.Guideword.UnintendedFunction ]
                description = "Unintended input arguments are used in a service method call. Therefore, the method call gets executed with wrong input data."
                failureeffect = "Communication of data-garbage, which could harm an overall safety goal."
                version = 1
                safety = ScoreReq.Asil.B
                rationale = "For all causes, we have either preventive measures or AoUs. Thus, no additional measures are required."
                // potentialcause = "A: Either the user interpreted the InArgs in the wrong layout or accesses the InArgs after return from the call. B: The mw::com implementation signals the call before all InArgs are provided or provides in-arg pointers to the wrong location."
            }

            // Fault-Tree $FailureMode [Communication.WrongMethodCalled]
            // Reference as mitigation measures:
            // - Wrongly configured: Is covered here: [ISSUE:Failuremode [InMemoryConfigurationWrong]
            // Reference as prevention measures:
            // - User Handler assignment wrong: ToDo: Requirement, that we make sure, that the user provided handlers are assigned to the right method and that the assignment is not corrupted and the lookup is safe.
            // - MethodId corrupted: ToDo: Requirement, that we assure, that the methodid gets not corrupted on its way from the caller to the callee and then also within the callee.
            ScoreReq.FailureMode WrongMethodCalled {
                guidewords = [ ScoreReq.Guideword.UnintendedFunction ]
                description = "Either the wrong user provided method handler is called or no user handler is called at all. Therefore, the method call results are invalid/garbage."
                failureeffect = "Communication of data-garbage, which could harm an overall safety goal."
                version = 1
                safety = ScoreReq.Asil.B
                rationale = "For all causes, we have either preventive measures or AoUs. Thus, no additional measures are required."
                // potentialcause = "A: The configuration between provider and consumer mismatches regarding method identification. B: The methodid used in assignment of user provided handlers is corrupted or the assignment/storage/lookup of the user provided handler fails."
            }

            // Fault-Tree $FailureMode [Communication.WrongResultsProvided]
            // Reference as mitigation measures:
            // - Callee provided result in wrong layout: Mitigated by AoU ScoreReq.AoU SameCompilerSettingsForProviderAndConsumerSide
            // - Callee signalled call finished before or without providing result completely: ToDo: Add an AoU, which states, that a user provided method handler always has to completely update the return-type reference before returning from its handler.
            // - Callee (user layer) concurrently updates result after returning from handler : ToDo: Eventually add an explicit/new AoU or extend the AoU ScoreReq.AoU ValidityOfPointerOnLoLaPointer for return value references, which states, that the user handler is not allowed to update any reference )by storing the address) after returning from a handler being called by mw::com.
            // Reference as prevention measures:
            // - Callee provided result in wrong location: ToDo: Requirement, that we make sure, that the result-reference provided to the user-handler is actually pointing to the right location, where the caller expects the result.
            // - Callee (mw::com layer) concurrently updates result after signaling call finished : ToDo: Requirement, that we make sure, that there is no write access to the result location after the method-return has been signalled to the caller.
            ScoreReq.FailureMode WrongResultsProvided {
                guidewords = [ ScoreReq.Guideword.UnintendedFunction ]
                description = "The result of a method call is either not provided in the expected location, leaving uninitialized data in the expected location or it is provided in an inconsistent state. Therefore, the method call results are invalid/garbage."
                failureeffect = "Communication of data-garbage, which could harm an overall safety goal."
                version = 1
                safety = ScoreReq.Asil.B
                rationale = "For all causes, we have either preventive measures or AoUs. Thus, no additional measures are required."
                // potentialcause = "A: The user handler either returns without providing a valid result or it writes it in an incorrect format. B: The user handler gets invoked with an invalid return-value reference."
            }
        }
    }
    section "Proxy" {

        section "Start Find Service" {

            // ID: 31546222
            ScoreReq.FailureMode StartFindServiceCallbackCalledUnexpectedly {
                guidewords = [ ScoreReq.Guideword.ExceedingFunction ]
                description = "The user-provided callback is invoked, even though it should not be invoked."
                failureeffect = "In the worst case, the callback is invoked all the time, which could lead to: The user thinks that a new proxy is found and creates a proxy with an already used handle; A DDoS is performed, where one thread is constantly blocked. Both can lead to violations of safety goals."
                version = 1
                safety = ScoreReq.Asil.B
                rationale = "Called even though StopFindService has been called, is tackled by the preventive measure: Proxy StopFindService. Called redundantly, is tackled by the preventive measure: \"Invoke FindServiceHandler...\" Wrong inotify events, are impossible, since these come from the OS, which is safety certified (no restriction found in the safety manual). Watches are set wrongly, is tackled by our preventive measure: Correct watches per Instance Identifier"
                // interface = "mw.com.Proxy.StartFindService"
            }
        }

        // Note. IsCurrentlyOffered means that the skeleton did everything correctly when setting up / offering the service. It doesn't consider issues when the skeleton offers the service.
        section "Find Service" {

            // ID: 6166029
            ScoreReq.FailureMode ServiceNotFoundButIsCurrentlyOffered {
                guidewords = [ ScoreReq.Guideword.LossOfFunction ]
                description = "A proxy does not find a service instance, even though it was offered by a skeleton."
                failureeffect = "No communication between process will happen, thus no information can be exchanged, thus any overall system functionality can stop."
                version = 1
                safety = ScoreReq.Asil.B
                rationale = ""
                // interface = "mw.com.Proxy.FindService"
            }

            // ID: 6166047
            ScoreReq.FailureMode WrongServiceFound {
                guidewords = [ ScoreReq.Guideword.UnintendedFunction ]
                description = "A proxy instance finds a wrong service. This could be either a wrong service instance or a completely wrong service."
                failureeffect = "The actual intended communication will not happen, thus potential causing a complete loss of system functionality. In the worst case, the wrong identifiers are used by another service. In that case a wrong consumer could think that he found the right service, leading to a case where garbage data is transmitted, causing any potential issues in the whole system functionality (e.g. violating the top level safety goal)."
                version = 1
                safety = ScoreReq.Asil.B
                rationale = "Both faults of wrongly configured and offered under wrong service IDs are covered by other analysis (Failuremode ServiceOfferedUnderWrongIds). For the InstanceSpecifier to Identifier we have the preventive measure \"InstanceSpecifier resolution can not retrieve wrong InstanceIdentifier resolution can not retrieve wrong InstanceIdentifier The last fault is covered by the ensured correct mapping of InstanceIdentifier to path."
                // interface = "mw.com.Proxy.FindService"
            }

            // ID: 6166060
            ScoreReq.FailureMode ServiceIsFoundButIsNotCurrentlyOffered {
                guidewords = [ ScoreReq.Guideword.ExceedingFunction ]
                description = "Finding a service, returns a service, even though no service instance was offered."
                failureeffect = "No communication between process will happen, thus no information can be exchanged, thus any overall system functionality can stop."
                version = 1
                safety = ScoreReq.Asil.B
                rationale = "The first root cause cannot happen, since otherwise the Operating System would make stupid stuff. mmap will not map any memory if a file does not exist. \"Service was offered, but not unlinked on stop offer\", is covered by our AoU that we do not notify on termination of the provider side. The other three faults are covered by the two preventive measures."
                // interface = "mw.com.Proxy.FindService"
            }
        }

        section "Construction" {

            ScoreReq.FailureMode ProxyCannotBeCreatedWithValidHandleWhenServiceIsOffered {
                guidewords = [ ScoreReq.Guideword.LossOfFunction ]
                description = "After finding a service and getting a valid handle (and the service has not been since or is currently being stop offered), creating a proxy with that handle fails."
                failureeffect = "No communication between process will happen, thus no information can be exchanged, thus any overall system functionality can stop."
                version = 1
                safety = ScoreReq.Asil.B
                rationale = ""
                // interface = "mw.com.Proxy.Create"
            }

            ' Proxy is created with different binding to skeleton

            ' ProxyEventCannotBeCreated 
            '     -> event name in interface must exist in configuration
            '     -> what happens if the configuration is different to the skeleton's configuration. 
            '            -> the event id doesn't exist in skeleton's configuration. i.e. the event id is different to the event id of the skeleton's config for the same event name
            '            -> the event id does exist but corresponds to a different event name. what happens if event id for a given name is wrong and matches to a different event name. It will then open the other event's EventDataSTorage but will access it with the wrong type
            '          measure for this would be to store the hash of the event name in event storage in shm to check that the event name / event id match. That way we can remove the existing AOU: Add an AoU that all code artifacts and configurations should be reviewed before use in a safety context.

            ' ProxyFieldCannotBeCreated

            ' ProxyMethodCannotBeCreated

        }

        section "Stop Find Service" {

            // ID: 31546507
            ScoreReq.FailureMode StartedFindServiceIsNotStopped {
                guidewords = [ ScoreReq.Guideword.LossOfFunction ]
                description = "A user called \"StartFindService\" with a given handler, and since \"StopFindService\" does not work, services can still be found."
                failureeffect = "StartFindService handler will be called, even though it is expected that it is not called."
                version = 1
                safety = ScoreReq.Asil.B
                rationale = "With the preventive measure, we ensure that this cannot happen."
                // potentialcause = "These cases are basically already covered here: [ISSUE:Failuremode StartFindServiceCallbackCalledUnexpectedly]"
            }

            // ID: 31546514
            ScoreReq.FailureMode WrongStartfindserviceIsStopped {
                guidewords = [ ScoreReq.Guideword.UnintendedFunction ]
                description = "The handle provided to StopFindService, is identified as another one and thus stops the wrong service discovery query."
                failureeffect = "That services are not found, even though they are offered and that services are no longer offered."
                version = 1
                safety = ScoreReq.Asil.B
                rationale = "Both potential effects are made clear to our customers via AoUs and is thus expected."
                // potentialcause = "Messed up handling of handles (only possibility, no tree needed)"
            }
        }

        section "Subscribe for an Event" {

            // ID: 6166213
            ScoreReq.FailureMode SubscribeToWrongEvent {
                guidewords = [ ScoreReq.Guideword.UnintendedFunction ]
                description = "A service proxy subscribes to a wrong event. This either means that this event does not exist at all, is offered by another service instance, another event in the current instance or a completely different service."
                failureeffect = "It is possible to allocate resources on another event and therefor block another valid subscription to this event. This could cause in the worst case that an safety relevant event cannot receive data, thus harming overall safety goals. Another case is that garbage data is transmitted / received. Causing any possible side-effect."
                version = 1
                safety = ScoreReq.Asil.B
                rationale = "All four root causes have been prevented by according measures each. * The name mapping clash in case of a GenericProxy is prevented by: ''Service-Element-Name clash needs to get unambigiously detected.'' * The referencing of wrong storage location is prevented by: ''Mapping from Event/Field identification to shared-memory storage needs to be unambigous.''"
            }

            // ID: 6166218
            ScoreReq.FailureMode SubscribeWithWrongMaxSampleCount {
                guidewords = [ ScoreReq.Guideword.PartialFunction ]
                description = "A proxy instance subscribes to an event to with a wrong sample count, meaning a different one that was provided by the user."
                failureeffect = "We have two possible effects: First if the number is lower then expected data of the user might be lost unexpectedly. Causing any possible side-effects. If its bigger, we could blocker other receiver which then get to few resources. Or the subscription fails at all. In the first two cases a possible safety goal violation could happen by not transmitting safety relevant data reliably."
                version = 1
                safety = ScoreReq.Asil.B
                rationale = "Both possible root cause are checked with preventive measures."
            }

            // ID: 6166225
            ScoreReq.FailureMode DoesNotSubscribe {
                guidewords = [ ScoreReq.Guideword.LossOfFunction ]
                description = "A proxy does not subscribe to a skeleton. Thus, a skeleton does not know that a proxy is interested in data."
                failureeffect = "A proxy will not be notified over new data. - This will lead to subscription state not changing to subscribed. And therefor a client application will not be able to access samples. This will lead to not receiving any safety relevant information, causing any possible safety goal violation. - Necessary resources might be blocked even though they are not reserved, causing potential blocks of other subscribers."
                version = 1
                safety = ScoreReq.Asil.B
                rationale = "-"
                // potentialcause = "the only possible fault is, that the shared memory segment or event is wrongly choosen, but this was already checked before while creating, so this can not really happen."
            }
        }

        section "SetReceiveHandler for an Event" {

            // ID: 6166297
            ScoreReq.FailureMode ReceiveHandlerNotInvoked {
                guidewords = [ ScoreReq.Guideword.LossOfFunction ]
                description = "A proxy has set a receive handler and a skeleton is updating an event, but the receive handler is never invoked."
                failureeffect = "It is possible that no event data is received ever and thus any safety issues are possible."
                version = 1
                safety = ScoreReq.Asil.B
                rationale = "N/A because root-cause covered by AoU."
                // interface = "score.mw.com.GenericProxyEvent.SetReceiveHandler"
                // potentialcause = "N/A because root-cause covered by AoU."
            }

            // ID: 6166301
            ScoreReq.FailureMode ReceiveHandlerInvokedWithWrongEvent {
                guidewords = [ ScoreReq.Guideword.UnintendedFunction ]
                description = "A receive handler registered for an event, gets called because of an update of an different event."
                failureeffect = "The only implication that this has are resource wise on timing. So a always notified handler could block one thread and thus make the overall system way more slow. The safety concept of the whole system supervises timely violations and ensures that no safety goal is harmed."
                version = 1
                safety = ScoreReq.Asil.B
                rationale = ""
                // interface = "score.mw.com.GenericProxyEvent.SetReceiveHandler"
            }

            // ID: 6166306
            ScoreReq.FailureMode ReceiveHandlerInvokedMultipleTimes {
                guidewords = [ ScoreReq.Guideword.ExceedingFunction ]
                description = "A receive handler is invoked multiple times, even though only one event update happend."
                failureeffect = "The only implication that this has are ressource wise on timing. So a always notified handler could block one thread and thus make the overall system way more slow. The safety concept of the whole system supervises timely violations and ensures that no safety goal is harmed."
                version = 1
                safety = ScoreReq.Asil.B
                rationale = "N/A because root-cause covered by AoU."
                // interface = "score.mw.com.GenericProxyEvent.SetReceiveHandler"
                // potentialcause = "N/A because root-cause covered by AoU."
            }

            // ID: 6166310
            ScoreReq.FailureMode ReceiveHandlerInvokedWithoutEventNotification {
                guidewords = [ ScoreReq.Guideword.ExceedingFunction ]
                description = "A receive handler is invoked, even though no event update happend."
                failureeffect = "A receive handler is invoked, even though no new events are available. The only implication that this has are ressource wise on timing. So a always notified handler could block one thread and thus make the overall system way more slow."
                version = 1
                safety = ScoreReq.Asil.B
                rationale = "N/A because root-cause covered by AoU."
                // interface = "score.mw.com.GenericProxyEvent.SetReceiveHandler"
                // potentialcause = "N/A because root-cause covered by AoU."
            }
        }

// Contract Subscribe:
//  - Subscribe can be called any number of times with the same max_sample_count. If calling Subscribe again (without having called Unsubscribe) 
//    with a different max_sample_count, ComErrc::kMaxSampleCountNotRealizable will be returned.

// Contracts:
//  - GetNewSamples will return an error ComErrc::kNotSubscribed if there hasn't been a successful Subscribe() or there was an Unsubscribe() since then
//  - The number of times the provided receiver is called can not be more than the minimum of:
//    - max_num_samples provided to GetNewSamples 
//    - the number of available SamplePtrs (The max_sample_count provided to the last successful call to Subscribe (which has not been unsubscribed) 
//      minus the number of currently held SamplePtrs from this ProxyEvent instance).
//  - The data pointed to by the SamplePtrs provided to receiver have the same values as the samples sent by SkeletonEvent::Send()
//  - The SamplePtrs provided to receiver will only point to samples received from SkeletonEvent::Send() since the last time successful call to GetNewSamples().
//  - The SamplePtrs provided to receiver will only point to samples sent by SkeletonEvent::Send() since the last time the service was succesfully offered.
//  - The SamplePtrs provided to receiver will always point to the latest samples sent by SkeletonEvent::Send()
//  - Returns the number of times the receiver was called
//  - Either calls the receiver with all available samples or returns an error (i.e. could call receiver but still return an error)
//
// Intended behaviour:
//  - All samples which have been sent by a successful SkeletonEvent::Send are provided to a call of GetNewSamples receiver (while still adhering to the preceding 
//    contracts e.g. regarding number of times receiver is called, must be subscribed etc).

        section "GetNewSamples for an Event" {

            ScoreReq.FailureMode ReturnsSuccessAlthoughNotInActiveSubscription {
                guidewords = [ ScoreReq.Guideword.UnintendedFunction ]
                description = "Subscribe was not called successfully or Unsubscribe has been called since a successful subscription and GetNewSamples does not return ComErrc::kNotSubscribed."
                failureeffect = "Getting samples without an active subscription could affect the ability of other ProxyEvents to receive samples which could lead to data availability issues."
                version = 1
                safety = ScoreReq.Asil.B
		        // interface = "score.mw.com.ProxyEvent.GetNewSamples"
            }

            ScoreReq.FailureMode ReturnsNotSubscribedErrorAthoughInActiveSubscription {
                guidewords = [ ScoreReq.Guideword.LossOfFunction ]
                description = "Subscribe was called successfully and Unsubscribe has not been called since and GetNewSamples returns ComErrc::kNotSubscribed"
                failureeffect = "Cannot receive data although data may be available"
                version = 1
                safety = ScoreReq.Asil.B
		        // interface = "score.mw.com.ProxyEvent.GetNewSamples"
            }

            ScoreReq.FailureMode ReturnsSuccessAlthoughDidNotCallReceiverCorrectNumberOfTimes {
                guidewords = [ ScoreReq.Guideword.UnintendedFunction ]
                description = "Receiver is not called the expected number of times (See ReceiverIsCalledMoreTimesThanAllowed and CallbackNotCalledWithSamplesReceivedFromSkeleton) but no error was returned"
                failureeffect = "Contract violation"
                version = 1
                safety = ScoreReq.Asil.B
		        // interface = "score.mw.com.ProxyEvent.GetNewSamples"
            }

            ScoreReq.FailureMode ReturnsAnErrorAlthoughCalledReceiverCorrectNumberOfTimes {
                guidewords = [ ScoreReq.Guideword.UnintendedFunction ]
                description = "Receiver is called the expected number of times (See ReceiverIsCalledMoreTimesThanAllowed and CallbackNotCalledWithSamplesReceivedFromSkeleton) but an error was returned"
                failureeffect = "Contract violation"
                version = 1
                safety = ScoreReq.Asil.B
		        // interface = "score.mw.com.ProxyEvent.GetNewSamples"
            }

            ScoreReq.FailureMode SamplePtrReturnedWhichWasReceivedBeforeLastGetNewSamples {
                guidewords = [ ScoreReq.Guideword.UnintendedFunction ]
                description = "Receiver called with SamplePtr pointing to old sample which was received from SkeletonEvent::Send before the last successful call to GetNewSamples which may have already been provided to a previous call to GetNewSamples."
                failureeffect = "Insertion of information / Repetition of information"
                version = 1
                safety = ScoreReq.Asil.B
		        // interface = "score.mw.com.ProxyEvent.GetNewSamples"
            }

            ScoreReq.FailureMode SamplePtrReturnedWhichWasSentBeforeLatestOfferService {
                guidewords = [ ScoreReq.Guideword.UnintendedFunction ]
                description = "Receiver called with SamplePtr pointing to old sample which was sent by SkeletonEvent::Send before the last successful call to Skeleton::OfferService."
                failureeffect = "Insertion of information"
                version = 1
                safety = ScoreReq.Asil.B
		        // interface = "score.mw.com.ProxyEvent.GetNewSamples"
            }
            
          // delete  ScoreReq.FailureMode CallbackNotCalledWithSampleDataNotReceivedFromSkeletonAlthoughSendSucceeded {
                guidewords = [ ScoreReq.Guideword.LossOfFunction ]
                description = "Skeleton has sent samples via SkeletonEvent::Send which returned success but they were never received on proxy side."
                failureeffect = "Deletion of information"
                version = 1
                safety = ScoreReq.Asil.B
                // rationale = "The wrong values are systematic faults wich are prevented using a correct slot allocation strategy. The overwrite of shared memory data was already built into the original design and can only happen if processes are started using wrong users, which is avoided using our AoU."
		        // interface = "score.mw.com.ProxyEvent.GetNewSamples"
            }

            // CallbackNotInvokedDespiteSamplesAvailable
            ScoreReq.FailureMode CallbackNotCalledAlthoughSkeletonSendSucceeded {
                guidewords = [ ScoreReq.Guideword.LossOfFunction ]
                description = "Receiver is not called the expected number of times although new samples were received from SkeletonEvent::Send and the number of currently available samples has not exceeded the maximum allowed (See ReceiverIsCalledMoreTimesThanAllowed)"
                failureeffect = "Data is not received"
                version = 1
                safety = ScoreReq.Asil.B
                // rationale = "The wrong values are systematic faults wich are prevented using a correct slot allocation strategy. The overwrite of shared memory data was already built into the original design and can only happen if processes are started using wrong users, which is avoided using our AoU."
		        // interface = "score.mw.com.ProxyEvent.GetNewSamples"
            }

            // CallbackInvokedWithWrongData
            ScoreReq.FailureMode DataPointedToBySamplePtrHasDifferentValueToSampleSentBySkeleton {
                guidewords = [ ScoreReq.Guideword.Corrupted ]
                description = "Receiver called with SamplePtr pointing to a sample whose value is different to the value sent via SkeletonEvent::Send"
                failureeffect = "Data is corrupted"
                version = 1
                safety = ScoreReq.Asil.B
                // rationale = "All possible faults, have either assigned a preventive measure or respective AoUs."
		        // interface = "score.mw.com.ProxyEvent.GetNewSamples"
            }

            // ID: 6166350
              // UsesTooManySampleptr
            ScoreReq.FailureMode ReceiverIsCalledMoreTimesThanAllowed {
                guidewords = [ ScoreReq.Guideword.ExceedingFunction ]
                description = "Receiver is called more than the allowed number of times. This number is the minimum of: 
		    (1) max number of samples provided to GetNewSamples. 
		    (2) the number of available SamplePtrs (The max_sample_count provided to the last successful call to Subscribe (which has not been unsubscribed) minus the number of currently held SamplePtrs from this ProxyEvent instance)."
                failureeffect = "Could allow a user to hold more SamplePrs than allowed which could affect the ability of other ProxyEvents to receive samples which could lead to data availability issues."
                version = 1
                safety = ScoreReq.Asil.B
                // rationale = "The only possibility for this failure mode is actively covered by our preventive measure."
		        // interface = "score.mw.com.ProxyEvent.GetNewSamples"
            }

            // ID: 6166353
            // ReturnsWrongSampleCount
            ScoreReq.FailureMode ReturnedCallCountDifferentToNumberOfTimesReceiverCalled {
                guidewords = [ ScoreReq.Guideword.UnintendedFunction ]
                description = "Value returned by GetNewSample() does not match with the number of calls to the receiver"
                failureeffect = "Contract violation"
                version = 1
                safety = ScoreReq.Asil.B
                rationale = "Single systematic failure is covered by single preventive measure."
		        // interface = "score.mw.com.ProxyEvent.GetNewSamples"
            }
        }

        section "GetFreeSampleCount for an Event" {

            // ID: 6166359
            ScoreReq.FailureMode ReturnsWrongFreeSampleCount {
                guidewords = [ ScoreReq.Guideword.UnintendedFunction ]
                description = "A user has already M SamplePtr in use from a max. announced number N, but GetFreeSampleCount() returns a different value than N-M."
                failureeffect = "It would be no longer possible to detect message losses on full queues."
                version = 1
                safety = ScoreReq.Asil.B
                rationale = "The correct implementation of GetFreeSampleCount() and of SamplePtr freeing of resources can only be tested together. Thus, both parts are covered via the same preventive measure."
                // potentialcause = "Internal counter of free and used samples broken."
            }
        }



• Repetition of information: A message is sent multiple times due to a stuck transmission buffer.
• Deletion of information: A message is dropped or lost in transit.
• Insertion of information: Rogue data, noise, or unassigned messages are injected into the bus.
• Incorrect sequence / Out-of-order: Messages arrive in the wrong order, causing outdated state inputs.
• Corruption of information: Bits are flipped during transmission due to Electromagnetic Interference (EMI) or hardware defects.
• Delay of information: A message is delayed beyond its maximum allowed transmission time (violating the fault tolerant time interval).
• Masquerading / Incorrect addressing: A component falsely identifies itself as a different sender, or a message is routed to the wrong node.

        section "Unsubscribe for an Event" {

            // ID: 6166363
            ScoreReq.FailureMode DoesNotUnsubscribe {
                guidewords = [ ScoreReq.Guideword.LossOfFunction ]
                description = "A proxy is subscribed to an event, tries to unsubscribe, but silently fails to unsubscribe."
                failureeffect = "Resource blockage on new subscriptions on other consumers. Maybe no communication possible."
                version = 1
                safety = ScoreReq.Asil.B
                rationale = "Message transmission failed, indicates an issue in our message passing library, which was already analyzed in [ISSUE:FailureMode SubscribeToWrongEvent] A proxy crash is not explicitly supported, with our partial restart feature."
            }

            // ID: 6166364
            ScoreReq.FailureMode UnsubscribesFromWrongEvent {
                guidewords = [ ScoreReq.Guideword.UnintendedFunction ]
                description = "A user unsubscribes from an event, but the unsubscribe is silently carried out on another event."
                failureeffect = "Same as Failuremode SubscribeToWrongEvent"
                version = 1
                safety = ScoreReq.Asil.B
                rationale = "If we unsubscribe to an wrong event, basically the same situation arises as if we would subscribe to a wrong event."
                // potentialcause = "Same as [ISSUE:Failuremode SubscribeToWrongEvent]"
            }

            // ID: 6166365
            ScoreReq.FailureMode DoesNotImplicitRemoveReceiveHandler {
                guidewords = [ ScoreReq.Guideword.PartialFunction ]
                description = "A proxy has registered a receive handler and unsubscribes, this should lead to the case that a receive handler is no longer called. In this failure mode, the receive handler would still be called."
                failureeffect = "Invocation of invalid receive handler, because it no longer exists. This could have any bad potential side effects."
                version = 1
                safety = ScoreReq.Asil.B
                rationale = "Only one possible failure that is covered with a preventive measure."
                // potentialcause = "Only possible fault is that the receive handler is not removed on unsubscription."
            }
        }

        section "Generic Proxy" {

            section "Generic access to Generic Proxy Events" {

                // ID: 31545325
                ScoreReq.FailureMode MapContainingNonexistentEvents {
                    guidewords = [ ScoreReq.Guideword.UnintendedFunction ]
                    description = "The map that is visible to the user, contains events that are not actually existing (e.g. in the configuration)."
                    failureeffect = "A user could take wrong actions based on this information and thus affect any safety goal."
                    version = 1
                    safety = ScoreReq.Asil.B
                    rationale = "Can only happen, if user misconfigures the system."
                }

                // ID: 31545231
                ScoreReq.FailureMode IncompleteMapOfEvents {
                    guidewords = [ ScoreReq.Guideword.PartialFunction ]
                    description = "The user gets presented not all events the generic proxy supports."
                    failureeffect = "Due to the map not complete, this will lead to missed data, because the user is not aware that these events are actually there. This could affect any safety goal."
                    version = 1
                    safety = ScoreReq.Asil.B
                    rationale = "Special case of [ISSUE:Failuremode MapContainingNonexistentEvents]"
                    // potentialcause = "Same as [ISSUE:Failuremode MapContainingNonexistentEvents]"
                }
            }

            section "Generic Proxy Event" {

                // ID: 31545522
                ScoreReq.FailureMode TheSizeReturnedIsBiggerThenTheActualValue {
                    guidewords = [ ScoreReq.Guideword.ExceedingFunction ]
                    description = "The user receives a size, that is bigger then the actual value."
                    failureeffect = "Undefined behavior due to wrong memory access."
                    version = 1
                    safety = ScoreReq.Asil.B
                    rationale = "A manipulated size is tackled, by \"Size information in read-only memory\". The right location is ensured via \"Location of type-meta-information information for Generic Proxy\" The wrong set size, is covered by \"The type-meta-information shall be calculated based on the provided event/field type"
                    // interface = "mw.com.GenericProxyEvent.GetDataTypeSizeInfo"
                }

                // ID: 31545538
                ScoreReq.FailureMode TheSizeReturnedIsSmallerThenTheActualSize {
                    guidewords = [ ScoreReq.Guideword.PartialFunction ]
                    description = "The user receives a size, that is smaller then the actual value."
                    failureeffect = "Only seeing a subset of the data, thus a potential violation of any safety goal."
                    version = 1
                    safety = ScoreReq.Asil.B
                    rationale = "Potential faults and measures are the same as [ISSUE:Failuremode TheSizeReturnedIsBiggerThenTheActualValue]"
                    // potentialcause = "Same as [ISSUE:Failuremode TheSizeReturnedIsBiggerThenTheActualValue]"
                    // interface = "mw.com.GenericProxyEvent.GetDataTypeSizeInfo"
                }

                // ID: 31545581
                ScoreReq.FailureMode WrongIndicationIfFormatIsSerialized {
                    guidewords = [ ScoreReq.Guideword.LossOfFunction ]
                    description = "A user, using HasSerializedFormat(), receives the wrong value."
                    failureeffect = "Missinterpretation of data, can lead to any safety violation."
                    version = 1
                    safety = ScoreReq.Asil.B
                    rationale = "Hard-coded value, not faults possible."
                    // potentialcause = "Hard-coded value, no faults possible."
                    // interface = "mw.com.GenericProxyEvent.HasSerializedFormat"
                }
            }
        }

        section "Call Method" {
            // Fault-Tree $FailureMode [Communication.CallBlocks]
            // Reference as mitigation for all three leaf-nodes/RootCauses in the fault-tree: ScoreReq.AoU [NoGuaranteesForTimelyMethodCallExecution]
            ScoreReq.FailureMode MethodCallBlocksLongerThanExpected {
                guidewords = [ ScoreReq.Guideword.DelayedFunction ]
                description = "A call to a service-method on the client/consumer side blocks longer than expected (or indefinite). This is a specific instance of FailureMode [AnyFunctionBlocksLongerThanExpected], but since with service-methods we have concrete root causes in the form of message-passing behaviour and behaviour of user-provided handler, we have this specific failure mode."
                failureeffect = "This could cause a halt of parts of/or the whole system."
                version = 1
                safety = ScoreReq.Asil.B
                rationale = "Our system anyhow imposes a watchdog to check for safety-related and time related paths. Thus, we do not try to safety qualify ever aspect and guarantee any execution timings."
                // potentialcause = "Underlying message-passing mechanism is blocked (e.g. the opposite side is not receiving messages) or the user provided handler is blocking."
            }

            // Fault-Tree $FailureMode [Communication.WrongInArgsProvided]
            // Reference as mitigation measures:
            // - Caller provided InArgs in wrong layout: Mitigated by AoU ScoreReq.AoU SameCompilerSettingsForProviderAndConsumerSide
            // - Caller updates InArgs concurrently after call signalling: Mitigated by AoU ScoreReq.AoU ValidityOfPointerOnLoLaPointer. ToDo: extend this AoU for MethodElementPtrs!
            // Reference as prevention measures:
            // - Call signalled before InArgs completely provided: ToDo: Requirement, that we make sure, that all MethodInArgPtrs are set/provided, before signalling the call.
            // - Caller provided InArgs in wrong location: ToDo: Requirement, that we make sure, that the provided MethodInArgPtrs are actually pointing to the right location.
            ScoreReq.FailureMode WrongMethodInArgsProvided {
                guidewords = [ ScoreReq.Guideword.UnintendedFunction ]
                description = "Unintended input arguments are provided to a service method call. Therefore, the method call gets executed with wrong input data."
                failureeffect = "Communication of data-garbage, which could harm an overall safety goal."
                version = 1
                safety = ScoreReq.Asil.B
                rationale = "For all causes, we have either preventive measures or AoUs. Thus, no additional measures are required."
                // potentialcause = "A: Either the user provides the InArgs in the wrong layout or updates the InArgs concurrently after call signalling. B: The mw::com implementation signals the call before all InArgs are provided or provides in-arg pointers to the wrong location."
            }

            // Fault-Tree $FailureMode [Communication.WrongResultsUsed]
            // Reference as mitigation measures:
            // - Caller used result in wrong layout: Mitigated by AoU ScoreReq.AoU SameCompilerSettingsForProviderAndConsumerSide
            // - Caller used result while concurrently updated: Mitigated by AoU ScoreReq.AoU ValidityOfPointerOnLoLaPointer. ToDo: extend this AoU for MethodElementPtrs!
            // Reference as prevention measures:
            // - Caller used result from wrong location: ToDo: Requirement, that we make sure, that MethodReturnPtr points to the correct location in shm.
            // - Caller used result before fully provided: ToDo: Requirement, that we make sure, that the MethodReturnPtr is only set/provided, when method call being signalled as finished.
            ScoreReq.FailureMode WrongReturnValueUsed {
                guidewords = [ ScoreReq.Guideword.UnintendedFunction ]
                description = "Unintended results are provided from a service method call. Therefore, the caller of the method works on wrong data."
                failureeffect = "Communication of data-garbage, which could harm an overall safety goal."
                version = 1
                safety = ScoreReq.Asil.B
                rationale = "For all causes, we have either preventive measures or AoUs. Thus, no additional measures are required."
                // potentialcause = "A: Either the user interpreted the Result in the wrong layout or accesses it after signalling, that he is done with its usage. B: The mw::com implementation signals the call being done before the return value is fully provided or provides result pointers to the wrong location."
            }
        }
    }




    section "SmartPointer" {

        section "SamplePtr and SampleAllocateePtr" {

            // ID: 6166375
            ScoreReq.FailureMode DoesNotFreeResourcesOnDestruction {
                guidewords = [ ScoreReq.Guideword.LossOfFunction ]
                description = "A SampleAllocateePtr or SamplePtr is destroyed, which should lead to a freeing of resources, but caused by a fault they are not freed."
                failureeffect = "Resource exhaustion. Could block further communication which could lead to failures on provider and consumer side, which on the other hand could lead to a violation of a safety goal."
                version = 1
                safety = ScoreReq.Asil.B
                rationale = "This failure mode can be avoided by ensuring an always valid slot and ensuring a correct slot-change logic. Which both is presented as preventive measure."
            }

            // ID: 6166378
            ScoreReq.FailureMode FreesWrongResources {
                guidewords = [ ScoreReq.Guideword.UnintendedFunction ]
                description = "A SampleAllocateePtr or SamplePtr free the wrong resources associated with them."
                failureeffect = "Communication of data-garbage or resource exhaustion, which both could harm an overall safety goal."
                version = 1
                safety = ScoreReq.Asil.B
                rationale = "Same as [ISSUE:Failuremode DoesNotFreeResourcesOnDestruction]"
                // potentialcause = "Same as [ISSUE:Failuremode DoesNotFreeResourcesOnDestruction] with the only difference that a slot could now be valid but the wrong one."
            }

            // ID: 6166381
            ScoreReq.FailureMode DoesNotReserveResources {
                guidewords = [ ScoreReq.Guideword.LossOfFunction ]
                description = "A SamplePtr or SampleAllocateePtr do not increase their respective ref-counts and thus avoid data changes."
                failureeffect = "Data is manipulated from different processes because they think its not owned. Which could cause garbage data and thus harm any safety goal."
                version = 1
                safety = ScoreReq.Asil.B
                rationale = "Same as [ISSUE:FailureMode DoesNotFreeResourcesOnDestruction] since a decrease of the ref-count has the same issues as an increase."
                // interface = "score.mw.com.SampleAllocateePtr<SampleType>"
            }

            // ID: 6166382
            ScoreReq.FailureMode DoesNotUpdateFreeSampleCountCorrectly {
                guidewords = [ ScoreReq.Guideword.LossOfFunction ]
                description = "When a SamplePtr gets created or destroyed for a given event instance, the Free Sample Count of this instance doesn't get updated accordingly"
                failureeffect = "Users may not know, if they are allowed to retrieve new Samples at all and may therefore fail to get new data! This may violate any safety goal."
                version = 1
                safety = ScoreReq.Asil.B
                rationale = "By ensuring a correct behavior of the SamplePtr, this fault can be omitted."
            }

            // ID: 6166385
            ScoreReq.FailureMode ReturnsWrongData {
                guidewords = [ ScoreReq.Guideword.UnintendedFunction ]
                description = "On dereferenciation of a SamplePtr or SampleAllocateePtr wrong data is returned."
                failureeffect = "If you cannot trust the data in the smart pointer, then the data can be garbage, which could break safe communication, which could harm any safety goal."
                version = 1
                safety = ScoreReq.Asil.B
                rationale = "The validity of the slot is ensured by a preventive measure, while the validity of the memory data is ensure by AoUs."
            }
        }

        section "MethodSignatureElementPtr" {

            // Fault-Tree $FailureMode [Communication.MethodSignatureElementPtrWrongTarget]
            // Reference as mitigation measures:
            // - References outdated valid memory inside shared-memory: Mitigated by AoU ScoreReq.AoU ValidityOfPointerOnLoLaPointer. ToDo: extend this AoU for MethodElementPtrs!
            // Reference as prevention measures:
            // - References wrong valid memory outside shared-memory: ToDo: This is either a lifetime issue (the memory was previously a mapped shm-region, which is now unmapped) or it was always in wrong memory, thus the following prevention holds.
            // - References wrong valid memory inside shared-memory: ToDo: Requirement, that we make sure, that the provided MethodSignatureElementPtrs are actually pointing to the right locations in shared-memory method-call-queues.
            // Reference as control measures:
            // - References invalid memory: Access to invalid memory leads to a crash, which harms availability but no safety goal.
            ScoreReq.FailureMode MethodSignatureElementPtrWrongTarget {
                guidewords = [ ScoreReq.Guideword.UnintendedFunction ]
                description = "On de-referencing of a MethodSignatureElementPtr wrong data is returned."
                failureeffect = "Resolution of the smart pointer to the wrong memory location, leads to garbage data access. This could harm any safety goal."
                version = 1
                safety = ScoreReq.Asil.B
                rationale = "The validity of the method signature element (return value/in-argument) is ensured by a preventive measure, while the validity of the data at this location is ensured by AoUs."
                // potentialcause = "A: The user didn't obey the lifetime rules of the MethodSignatureElementPtr and thus accesses it after it has been invalidated. B: The pointers were either wrongly initialized or point to locations, which were invalidated before the access happens."
            }

            // Fault-Tree $FailureMode [Communication.MethodSignatureElementPtrFailsToFree]
            // Reference as mitigation measures:
            // - Does not free method signature element: Mitigated by AoU ScoreReq.AoU [NoGuaranteesForTimelyMethodCallExecution]
            // Reference as prevention measures:
            // - Overwrite of element in use: ToDo: Requirement, that we make sure, that the provided MethodSignatureElementPtrs are actually pointing to the right locations in shared-memory method-call-queues and no double use takes place.
            ScoreReq.FailureMode MethodSignatureElementPtrFailsToFree {
                guidewords = [ ScoreReq.Guideword.LossOfFunction ]
                description = "On destruction of a MethodSignatureElementPtr wrong memory is freed or not freed at all."
                failureeffect = "Failing to free resources can lead to a loss of function as no further method calls could be processed. This does not harm a safety goal. But freeing the wrong resources could lead to This could harm any safety goal."
                version = 1
                safety = ScoreReq.Asil.B
                rationale = "Not freeing a method signature element within a call-queue would lead to a further call to be blocked, but since we anyhow do not guarantee any execution timing, this is not a safety issue. Freeing the wrong memory can be tackled by ensuring that the MethodSignatureElementPtrs always point to the right location in shared-memory method-call-queues."
                // potentialcause = "A: Pointer got corrupted and therefore points to the wrong location. B: The location, where the pointer points to, was falsely re-used."
            }
        }
    }
}
