/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/

package AouForwardingTest

import ScoreReq
import Communication

ScoreReq.CompReq COMP_FORWARDING_TEST_001 {
    description = "The component shall handle the forwarded Communication MonotonicSemiDynamicMemoryAllocation assumption of use."
    safety = ScoreReq.Asil.B
    derived_from = [Communication.MonotonicSemiDynamicMemoryAllocation@1]
    version = 1
}
