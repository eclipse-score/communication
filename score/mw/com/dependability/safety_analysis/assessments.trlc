/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package Communication

import ScoreReq
import mw_com_fta

ScoreReq.RootCauseAssessment DummyAssessment {
    root_causes = [mw_com_fta.ActivelyManipulateByProgrammParts]
    measures    = []
    safety      = ScoreReq.Asil.B
    rationale   = "Dummy placeholder. No assessment performed."
    version     = 1
}
