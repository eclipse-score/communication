/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package ServiceDiscovery

import ScoreReq

ScoreReq.AoU DaemonStartedBeforeClients {
    description = "The service discovery daemon shall be started before service providers and consumers initiate registration or lookup calls."
    note = "Client and provider startup depends on an already reachable daemon session endpoint."
    safety = ScoreReq.Asil.B
    version = 1
}

ScoreReq.AoU SingleDaemonAuthority {
    description = "Exactly one service discovery daemon instance shall act as registry authority at a time."
    note = "This is a deployment and integration precondition; component requirements only govern behavior within a single running daemon instance."
    safety = ScoreReq.Asil.B
    version = 2
}
