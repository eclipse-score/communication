/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package ServiceDiscovery

import ScoreReq

section "System Requirements" {

ScoreReq.CompReq SingleActiveRegistryAuthority {
    description = "Within one service discovery daemon process instance, the service discovery component shall ensure that only one daemon authority accepts registry write operations at a time."
    safety = ScoreReq.Asil.B
    derived_from = [ServiceDiscovery.DaemonBasedRegistry@2]
    version = 3
}

ScoreReq.CompReq DaemonCommunicationUsesMessagePassing {
    description = "The service discovery component shall use same-host platform message passing for daemon communication on Linux and QNX."
    safety = ScoreReq.Asil.B
    derived_from = [
        ServiceDiscovery.DaemonBasedRegistry@2,
        ServiceDiscovery.OsIndependentDaemonProtocol@2,
    ]
    version = 2
}

ScoreReq.CompReq RegistrySupportsServiceKeyLookup {
    description = "The service discovery component shall resolve service offers using a service key tuple of service identifier and instance identifier."
    safety = ScoreReq.Asil.B
    derived_from = [ServiceDiscovery.DeterministicLookupBehavior@2]
    version = 2
}

ScoreReq.CompReq RuntimeMaintainsDaemonSession {
    description = "The service discovery runtime shall establish a daemon message-passing session when a client initializes service discovery usage and shall release the session-owned state when that client runtime shuts down or disconnects."
    safety = ScoreReq.Asil.B
    derived_from = [ServiceDiscovery.SessionBoundClientLifecycle@2]
    version = 3
}

ScoreReq.CompReq RegistrySupportsAnyInstanceLookup {
    description = "The service discovery component shall support lookup and search requests that match any instance of a given service identifier."
    safety = ScoreReq.Asil.B
    derived_from = [ServiceDiscovery.AnyInstanceServiceSelection@2]
    version = 2
}

ScoreReq.CompReq StaticOfferAuthorizationLoadedAtStartup {
    description = "The daemon shall accept a startup configuration that defines which UIDs are authorized to offer configured service instances."
    safety = ScoreReq.Asil.B
    derived_from = [ServiceDiscovery.StaticOfferAuthorizationPolicy@2]
    version = 2
}

}

section "Behaviour Requirements" {

ScoreReq.CompReq RegisterRejectsIntegrityEscalation {
    description = "The service discovery daemon shall reject a registration request when the provider integrity is lower than the offered service integrity."
    safety = ScoreReq.Asil.B
    derived_from = [ServiceDiscovery.PartitionedVisibilityForIntegrityLevels@2]
    version = 2
}

ScoreReq.CompReq UnregisterChecksOwnership {
    description = "The service discovery daemon shall remove a registration only when the unregister request identity matches the original provider identity."
    safety = ScoreReq.Asil.B
    derived_from = [ServiceDiscovery.PartitionedVisibilityForIntegrityLevels@2]
    version = 2
}

ScoreReq.CompReq LookupReturnsConsistentSnapshot {
    description = "The service discovery daemon shall return lookup results from one atomically captured registry state for each lookup request."
    safety = ScoreReq.Asil.B
    derived_from = [ServiceDiscovery.DeterministicLookupBehavior@2]
    version = 2
}

ScoreReq.CompReq StaleEntriesAreRemoved {
    description = "The service discovery daemon shall remove registrations no later than the next supervision cycle after their configured liveness deadline is exceeded."
    safety = ScoreReq.Asil.B
    derived_from = [ServiceDiscovery.StaleEntrySupervision@2]
    version = 2
}

ScoreReq.CompReq StartFindServiceReturnsSnapshotAndHandle {
    description = "The service discovery daemon shall return the current matching service-instance snapshot and a daemon-issued search handle in response to a start-find request."
    safety = ScoreReq.Asil.B
    derived_from = [
        ServiceDiscovery.AsyncServiceDiscoveryUpdates@2,
        ServiceDiscovery.DeterministicLookupBehavior@2,
    ]
    version = 2
}

ScoreReq.CompReq SearchHandleControlsNotifications {
    description = "The service discovery daemon shall stop availability notifications for a search after the matching stop-find request for its handle is accepted."
    safety = ScoreReq.Asil.B
    derived_from = [ServiceDiscovery.AsyncServiceDiscoveryUpdates@2]
    version = 2
}

ScoreReq.CompReq ConnectionLossRemovesOwnedState {
    description = "The service discovery daemon shall remove registrations, active searches, and daemon-managed locks that are owned by a disconnected client session."
    safety = ScoreReq.Asil.B
    derived_from = [ServiceDiscovery.SessionBoundClientLifecycle@2]
    version = 2
}

ScoreReq.CompReq RegisterRejectsUnauthorizedOfferer {
    description = "The service discovery daemon shall reject a register request when the caller UID is not authorized for the requested service instance by the static offer policy."
    safety = ScoreReq.Asil.B
    derived_from = [ServiceDiscovery.StaticOfferAuthorizationPolicy@2]
    version = 2
}

ScoreReq.CompReq ServiceCreationLockIsExclusive {
    description = "The service discovery daemon shall provide an exclusive service-creation lock so that at most one provider may prepare a given service instance at a time."
    safety = ScoreReq.Asil.B
    derived_from = [ServiceDiscovery.DaemonManagedServiceInstanceLocks@2]
    version = 2
}

ScoreReq.CompReq ServiceCreationLockReleasedOnUnregisterOrDisconnect {
    description = "The service discovery daemon shall release a service-creation lock automatically when its owner unregisters the service instance or disconnects."
    safety = ScoreReq.Asil.B
    derived_from = [
        ServiceDiscovery.DaemonManagedServiceInstanceLocks@2,
        ServiceDiscovery.SessionBoundClientLifecycle@2,
    ]
    version = 2
}

ScoreReq.CompReq ServiceUsageLockSupportsSharedAndExclusiveModes {
    description = "The service discovery daemon shall provide service-usage lock operations with shared mode for consumers and exclusive mode for providers."
    safety = ScoreReq.Asil.B
    derived_from = [ServiceDiscovery.DaemonManagedServiceInstanceLocks@2]
    version = 2
}

ScoreReq.CompReq ServiceUsageLocksReleasedOnDisconnect {
    description = "The service discovery daemon shall release service-usage locks automatically when the owning client session disconnects."
    safety = ScoreReq.Asil.B
    derived_from = [
        ServiceDiscovery.DaemonManagedServiceInstanceLocks@2,
        ServiceDiscovery.SessionBoundClientLifecycle@2,
    ]
    version = 2
}

ScoreReq.CompReq BatchedOperationsPreservePerCallResults {
    description = "The service discovery daemon shall process each batch request in input order and return one result entry per input operation in the same order."
    safety = ScoreReq.Asil.B
    derived_from = [ServiceDiscovery.BatchedDaemonOperations@2]
    version = 2
}

}

section "API Requirements" {

ScoreReq.CompReq RegistryRegisterApi {
    description = "The registry interface shall provide a Register operation that accepts service key, endpoint, integrity, and provider identity."
    safety = ScoreReq.Asil.B
    derived_from = [ServiceDiscovery.DaemonBasedRegistry@2]
    version = 2
}

ScoreReq.CompReq RegistryUnregisterApi {
    description = "The registry interface shall provide an Unregister operation that accepts service key and provider identity."
    safety = ScoreReq.Asil.B
    derived_from = [ServiceDiscovery.DaemonBasedRegistry@2]
    version = 2
}

ScoreReq.CompReq RegistryResolveApi {
    description = "The registry interface shall provide a Resolve operation that returns all registrations matching the requested service key from one registry snapshot."
    safety = ScoreReq.Asil.B
    derived_from = [ServiceDiscovery.DeterministicLookupBehavior@2]
    version = 2
}

ScoreReq.CompReq ProtocolEncodesRegisterUnregisterResolve {
    description = "The daemon protocol shall encode register, unregister, and resolve operations with fixed byte order and deterministic field layout."
    safety = ScoreReq.Asil.B
    derived_from = [ServiceDiscovery.OsIndependentDaemonProtocol@2]
    version = 3
}

ScoreReq.CompReq ProtocolEncodesAsyncDiscoveryUpdates {
    description = "The daemon protocol shall encode subscribe, unsubscribe, and availability-notification operations with fixed byte order and deterministic field layout."
    safety = ScoreReq.Asil.B
    derived_from = [ServiceDiscovery.AsyncServiceDiscoveryUpdates@2]
    version = 3
}

ScoreReq.CompReq ProtocolEncodesStartAndStopFindService {
    description = "The daemon protocol shall encode start-find and stop-find request-reply operations, and each start-find reply shall contain an initial result snapshot and a unique search handle within the daemon process lifetime."
    safety = ScoreReq.Asil.B
    derived_from = [
        ServiceDiscovery.AsyncServiceDiscoveryUpdates@2,
        ServiceDiscovery.AnyInstanceServiceSelection@2,
    ]
    version = 2
}

ScoreReq.CompReq ProtocolEncodesDaemonManagedLockOperations {
    description = "The daemon protocol shall encode service-creation lock and service-usage lock operations with fixed byte order and deterministic field layout."
    safety = ScoreReq.Asil.B
    derived_from = [ServiceDiscovery.DaemonManagedServiceInstanceLocks@2]
    version = 3
}

ScoreReq.CompReq ProtocolEncodesBatchRequests {
    description = "The daemon protocol shall encode batched daemon operations with explicit operation boundaries and an ordered result list within one request-reply exchange."
    safety = ScoreReq.Asil.B
    derived_from = [ServiceDiscovery.BatchedDaemonOperations@2]
    version = 2
}

ScoreReq.CompReq AuthorizationPolicyConfigurationApi {
    description = "The service discovery component shall provide a configuration interface for loading the static offer-authorization policy into the daemon at startup."
    safety = ScoreReq.Asil.B
    derived_from = [ServiceDiscovery.StaticOfferAuthorizationPolicy@2]
    version = 2
}

ScoreReq.CompReq ServiceDiscoveryCompatibilityFacade {
    description = "The service discovery component shall provide a compatibility facade that preserves the current IServiceDiscovery API shape while delegating to the daemon-backed implementation."
    safety = ScoreReq.Asil.B
    derived_from = [ServiceDiscovery.DaemonBasedRegistry@2, ServiceDiscovery.AsyncServiceDiscoveryUpdates@2]
    version = 2
}

}
