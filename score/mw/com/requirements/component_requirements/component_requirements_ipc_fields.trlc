/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package Communication

import ScoreReq

section "com" {
    section "Public_API_Requirements" {

        ScoreReq.CompReq FieldGetAndSetInterfaceDefinition{

            description = """On the interface definition level of a field it shall be possible to specify for each of the following functionalities, whether they are enabled or not:
    - support for a `Get()` call to retrieve the current field value
    - support for a `Set()` call to set the current field value
    - support for a notification to registered consumers to a field update."""
            safety = ScoreReq.Asil.B
            derived_from = [Communication.Field@1]
            version = 1
        }


        ScoreReq.CompReq NoSupportForNotificationInSharedMemoryBinding {

            description = """For the field implementation in our shared-memory-binding implementation, the setting for "support for a notification" specified in [[FieldGetAndSetInterfaceDefinition]] shall be ignored. This is because, in the shared-memory-binding implementation support for update notification does not imply any performance drawbacks, unlike, for example a network binding.""" safety = ScoreReq.Asil.B
            derived_from = [Communication.Field@1, Communication.MultiBindingSupport@1]
            version = 1
        }

    }

    section "Field_member_representation_at_the_Proxy_side" {

        ScoreReq.CompReq GetMethodOnlyIfEnabledInInterfaceDefinition {
            description="""It shall provide a public `Get` method only in the case, that 'support for a `Get()`' has been enabled in the underlying interface definition (see [[FieldGetAndSetInterfaceDefinition]])"""
            derived_from = [Communication.Field@1]
            version = 1

        }

        ScoreReq.CompReq  GetMethodSignature {
            description=""" The signature of the `Get` method shall be: `score::Result<MethodReturnTypePtr<SampleDataType>> Get()`."""
            derived_from = [Communication.Field@1]
            version = 1

        }


        ScoreReq.CompReq GetMethodReturnValue {
             description="""It shall return the provider's most recently updated field value as a `MethodReturnTypePtr` upon success."""
                derived_from = [Communication.Field@1, Communication.ProducerConsumerPattern@1]
                version = 1

        }

        ScoreReq.CompReq SetMethodOnlyIfEnabledInInterfaceDefinition {
                description="""It shall provide a public `Set` method only in the case, that "support for a Set()" has been enabled in the underlying interface definition (see [[FieldGetAndSetInterfaceDefinition]])."""
                derived_from = [Communication.Field@1]
                version = 1
        }

        ScoreReq.CompReq SetMethodSignature {
                description=""" The signature of the `Set` method shall be: `score::Result<MethodReturnTypePtr<SampleDataType>> Set(MethodInArgPtr<SampleDataType>)`"""
                derived_from = [Communication.Field@1]
                version = 1
        }

        ScoreReq.CompReq SetMethodReturnValue {
                description="""`Set` method shall return the provider’s latest updated field value as a `MethodReturnTypePtr` on success."""
                derived_from = [Communication.Field@1, Communication.ProducerConsumerPattern@1]
                version = 1
        }

        ScoreReq.CompReq  AllocateMethodForZeroCopySet {
                description="""It shall provide a `Allocate()` method for the zero-copy Set call variant."""
                derived_from = [Communication.Field@1, Communication.ZeroCopy@1]
                version = 1
        }

        ScoreReq.CompReq  AllocateMethodSignature {
                description="""The signature of the `Allocate()` method shall be: `score::Result<impl::MethodInArgPtr<SampleDataType>> Allocate()`."""
                derived_from = [Communication.Field@1, Communication.ZeroCopy@1]
                version = 1
        }


        ScoreReq.CompReq  ZeroCopySetMethodOnlyIfEnabledInInterfaceDefinition {
                description="""It shall provide a public `Set` method with zero copy semantics only in the case, that "support for a Set()" has been enabled in the underlying interface definition (see [[FieldGetAndSetInterfaceDefinition]])."""
                derived_from = [Communication.Field@1, Communication.ZeroCopy@1]
                version = 1
        }

        ScoreReq.CompReq   ZeroCopySetMethodSignature {
                description="""The signature of the `Set` method shall be: `score::Result<MethodReturnTypePtr<SampleDataType>> Set(MethodInArgPtr<SampleDataType>)`"""
                derived_from = [Communication.Field@1, Communication.ZeroCopy@1]
                version = 1
        }

    }

    section "Field_member_representation_at_the_Skeleton_side" {

        ScoreReq.CompReq RegisterSetHandlerOnlyIfEnabledInInterfaceDefinition {
            description="""It shall provide a public `RegisterSetHandler` method only in the case, that "support for a Set()" has been enabled in the underlying interface definition (see [[FieldGetAndSetInterfaceDefinition]])"""
            derived_from = [Communication.Field@1]
            version = 1
        }

        ScoreReq.CompReq RegisterSetHandlerSignature {
            description=""" The signature of the `RegisterSetHandler` method shall be: `score::ResultBlank RegisterSetHandler(SetHandlerType)`"""
            derived_from = [Communication.Field@1]
            version = 1
        }

        ScoreReq.CompReq SetHandlerTypeDefinition {
            description="""The `SetHandlerType` shall be a callable of this type: using SetHandlerType = score::cpp::callback<void(SampleDataType&)>;`"""
            derived_from = [Communication.Field@1]
            version = 1
        }

        ScoreReq.CompReq SetHandlerMandatoryIfSetEnabledInInterfaceDefinition {
            description="""It is mandatory to register a `SetHandler` for a `SkeletonField` instance, in case Set has been enabled in the underlying interface definition. If the user has not registered a handler before calling `Offer()` on the enclosing skeleton, the call to `Offer()` shall fail with an error."""
            derived_from = [Communication.Field@1, Communication.ServiceInstance@1]
            version = 1
        }


        ScoreReq.CompReq SetHandlerReturnValueAndNotification {
            description="""After the user provided `SetHandler` has returned, the (potentially updated) field value has to:
- be stored as the latest value.
- if notification has been enabled as per the interface definition (see [[FieldGetAndSetInterfaceDefinition]]), notifier for the updated value has to be called to inform subscribers of the field about the updated value.
- be returned as the result of the `get()` method call to the proxy side."""
            derived_from = [Communication.Field@1, Communication.ProducerConsumerPattern@1]
            version = 1
        }

    }

}
