/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package MessagePassingSEooC

import ScoreReq

///////////////////////////////
// Feature Requirements
// Integration level requirements derived from Assumed System Requirements
///////////////////////////////

// TODO: Add feature requirements for message passing
// Example:
/*
ScoreReq.FeatReq FEAT_MP_001 {
    description = "The message passing component shall provide a server interface that registers connection handlers and processes incoming requests."
    safety = ScoreReq.Asil.B
    derived_from = [MessagePassingSEooC.ASR_MP_001@1]
    version = 1
}

ScoreReq.FeatReq FEAT_MP_002 {
    description = "The message passing component shall provide a client interface for sending requests to a server and receiving responses."
    safety = ScoreReq.Asil.B
    derived_from = [MessagePassingSEooC.ASR_MP_001@1]
    version = 1
}
*/
