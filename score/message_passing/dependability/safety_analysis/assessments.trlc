/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package MessagePassing

import ScoreReq
import message_passing_fta

ScoreReq.RootCauseAssessment DummyAssessment {
    root_causes = [message_passing_fta.OsIpcFaultHandling]
    measures    = []
    safety      = ScoreReq.Asil.B
    rationale   = "Dummy placeholder. No assessment performed."
    version     = 1
}
