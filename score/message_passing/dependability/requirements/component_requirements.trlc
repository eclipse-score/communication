/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package MessagePassing

import ScoreReq

section "Platform Requirements" {

ScoreReq.CompReq SafetyCertifiedTransportMechanismUnderQNX {
    description = "On the QNX operating system, the message passing component shall use the QNX-message-passing as the underlying IPC mechanism."
    safety = ScoreReq.Asil.B
    derived_from = [MessagePassing.SafetyCertifiedTransportMechanism@2, MessagePassing.OSIndependentAPI@2]
    version = 1
}

ScoreReq.CompReq TransportMechanismOnLinux {
    description = "On the Linux operating system, the message passing component shall use unix domain-sockets as the underlying IPC mechanism."
    note = "Lowered from ASIL B to QM: ASIL compliance is not currently pursued on Linux, which is used for host development and testing. The safety-certified transport for ASIL B is QNX-native messaging on QNX (see SafetyCertifiedTransportMechanismUnderQNX). A derived requirement must not have a lower ASIL than its parents, so this record derives neither from SafetyCertifiedTransportMechanism nor from OSIndependentAPI, but only from QMImplementationOnNonQnxOS, the feature-level capability this record's QM Linux implementation fulfills. That the Linux implementation provides the same OS-independent API is expressed by the architecture, not by derivation."
    safety = ScoreReq.Asil.QM
    derived_from = [MessagePassing.QMImplementationOnNonQnxOS@1]
    version = 4
}

ScoreReq.CompReq OSProvidedClientIdentityPerConnection {
    description = "The message passing server shall identify the client of a Server Connection once, when the connection is accepted, by the client's OS-provided process ID (PID), user ID (UID), and primary group ID (GID)."
    note = "Replaces the retired OSProvidedSenderIdentity record: identification is established once per Server Connection, not re-derived per message, and now names all three OS-provided identifiers instead of only the UID."
    safety = ScoreReq.Asil.B
    derived_from = [MessagePassing.ServerInterface@2]
    version = 1
}

}

section "Behaviour Requirements" {

ScoreReq.CompReq ServerCallbacksAreSequential {
    description = "The server shall serialize all callbacks belonging to the same server instance, such that no two such callbacks execute concurrently."
    safety = ScoreReq.Asil.B
    derived_from = [MessagePassing.ServerInterface@2]
    version = 1
}

ScoreReq.CompReq ServerProcessesSinglePendingRequest {
    description = "The server shall not dispatch a new sent-with-reply message callback on a given `ServerConnection` until the preceding request has been replied to."
    safety = ScoreReq.Asil.B
    derived_from = [MessagePassing.SynchronousBidirectionalCommunication@2]
    version = 1
}

ScoreReq.CompReq ClientConnectionMaintainsStateMachine {
    description = "The `ClientConnection` shall maintain a state machine with the states `Starting`, `Ready`, `Stopping`, and `Stopped`."
    safety = ScoreReq.Asil.B
    derived_from = [MessagePassing.ClientInterface@1]
    version = 2
}

ScoreReq.CompReq ClientSendUsesDirectTransportCallByDefault {
    description = "The `ClientConnection` shall issue the `Send` message via an immediate OS-level transport call, which may block the calling thread, unless `ClientConfig::truly_async` is configured, or a `SendWaitReply`/`SendWithCallback` reply is currently pending on the same connection while `ClientConfig::fully_ordered` is configured."
    note = "Replaces the retired `SynchronousSendBlocksUntilServerReceives`, whose condition ('no client-side send queue configured') did not match the implementation: the direct-call path is selected by `!ClientConfig::fully_ordered && !ClientConfig::truly_async` (plus the pending-reply exception above), independent of `ClientConfig::max_queued_sends`. Blocking, when it occurs, is bounded by the OS transport call itself, not by receiver-side processing; see `SynchronousUnidirectionalCommunication` for the corresponding feature-level asymmetry between backends."
    safety = ScoreReq.Asil.B
    derived_from = [MessagePassing.SynchronousUnidirectionalCommunication@3]
    version = 1
}

ScoreReq.CompReq ClientSendQueuesForAsyncOrOrderingReasons {
    description = "The `ClientConnection` shall enqueue the `Send` message for asynchronous delivery by the background transport, returning after local acceptance, whenever `ClientConfig::truly_async` is configured, or whenever a `SendWaitReply`/`SendWithCallback` reply is currently pending on the same connection while `ClientConfig::fully_ordered` is configured."
    note = "Replaces the retired `AsynchronousSendReturnsAfterLocalAcceptance`, whose condition ('a client-side send queue is configured') did not match the implementation: `ClientConfig::max_queued_sends` being nonzero alone does not trigger queuing."
    safety = ScoreReq.Asil.B
    derived_from = [MessagePassing.AsynchronousUnidirectionalCommunication@3]
    version = 1
}

ScoreReq.CompReq SendWaitReplyBlocksUntilServerReply {
    description = "The ClientConnection shall block the calling thread during a SendWaitReply call until a reply from the server is received or an error is detected."
    safety = ScoreReq.Asil.B
    derived_from = [MessagePassing.SynchronousBidirectionalCommunication@2]
    version = 1
}

ScoreReq.CompReq MessageOrderPreservationPerConnection {
    description = "The message passing component shall deliver messages of the same delivery type from the same `IClientConnection` instance to the server in the order they were sent."
    safety = ScoreReq.Asil.B
    derived_from = [MessagePassing.PointToPointConnections@2]
    version = 1
}

ScoreReq.CompReq SingleServerInstancePerServiceIdentifier {
    description = "The message passing component shall prevent more than one active `IServer` instance serves any given service identifier at any point in time."
    safety = ScoreReq.Asil.B
    derived_from = [MessagePassing.PointToPointConnections@2]
    version = 1
}

}

section "API Requirements" {

ScoreReq.CompReq IServerStartListeningAPI {
    description = "`IServer` shall provide a `StartListening` method that registers connection, disconnection, fire-and-forget message, and sent-with-reply message callbacks."
    safety = ScoreReq.Asil.B
    derived_from = [MessagePassing.ServerInterface@2]
    version = 1
}

ScoreReq.CompReq IServerStopListeningAPI {
    description = "`IServer` shall provide a `StopListening` method that releases all registered callbacks and closes all active server connections."
    safety = ScoreReq.Asil.B
    derived_from = [MessagePassing.ServerInterface@2]
    version = 1
}

ScoreReq.CompReq IClientConnectionSendAPI {
    description = "`IClientConnection` shall provide a Send method that accepts a byte-span message and transmits it to the server."
    safety = ScoreReq.Asil.B
    derived_from = [MessagePassing.SynchronousUnidirectionalCommunication@3]
    version = 1
}

ScoreReq.CompReq IClientConnectionSendWaitReplyAPI {
    description = "`IClientConnection` shall provide a `SendWaitReply` method that accepts a message byte span and a reply buffer span and returns the received reply payload trimmed to its actual size."
    safety = ScoreReq.Asil.B
    derived_from = [MessagePassing.SynchronousBidirectionalCommunication@2]
    version = 1
}

ScoreReq.CompReq IClientConnectionSendWithCallbackAPI {
    description = "`IClientConnection` shall provide a `SendWithCallback` method that accepts a message byte span and a reply callback and returns after the message has been accepted by the local message passing layer."
    safety = ScoreReq.Asil.B
    derived_from = [MessagePassing.AsynchronousUnidirectionalCommunication@3]
    version = 1
}

ScoreReq.CompReq IServerConnectionReplyAPI {
    description = "`IServerConnection` shall provide a Reply method that accepts a byte-span message and delivers it as the reply to the pending REQUEST from the client."
    safety = ScoreReq.Asil.B
    derived_from = [MessagePassing.SynchronousBidirectionalCommunication@2]
    version = 1
}

ScoreReq.CompReq IServerConnectionNotifyAPI {
    description = "`IServerConnection` shall provide a `Notify` method that accepts a byte-span message and sends it as an asynchronous notification to the client."
    safety = ScoreReq.Asil.B
    derived_from = [MessagePassing.AsynchronousServerNotification@1]
    version = 2
}

ScoreReq.CompReq ClientFactoryCreateAPI {
    description = "`IClientFactory` shall provide a `Create` method that accepts a `ServiceProtocolConfig` and a `ClientConfig` and returns a new `IClientConnection` instance configured for the service specified by the `ServiceProtocolConfig`."
    safety = ScoreReq.Asil.B
    derived_from = [MessagePassing.OSIndependentAPI@2]
    version = 1
}

ScoreReq.CompReq ServerFactoryCreateAPI {
    description = "`IServerFactory` shall provide a `Create` method that accepts a `ServiceProtocolConfig` and a `ServerConfig` and returns a new `IServer` instance configured for the service specified by the `ServiceProtocolConfig`."
    safety = ScoreReq.Asil.B
    derived_from = [MessagePassing.OSIndependentAPI@2]
    version = 1
}

ScoreReq.CompReq ClientFactoryEngineSharingAPI {
    description = "`ClientFactory` shall provide a constructor accepting a `shared_ptr<Engine>` and a `GetEngine` accessor, so that it can share a single `Engine` instance with other `ClientFactory`/`ServerFactory` instances in the same process instead of each owning its own."
    safety = ScoreReq.Asil.B
    derived_from = [MessagePassing.SingletonFreeImplementation@2]
    version = 1
}

ScoreReq.CompReq ServerFactoryEngineSharingAPI {
    description = "`ServerFactory` shall provide a constructor accepting a `shared_ptr<Engine>` and a `GetEngine` accessor, so that it can share a single `Engine` instance with other `ClientFactory`/`ServerFactory` instances in the same process instead of each owning its own."
    safety = ScoreReq.Asil.B
    derived_from = [MessagePassing.SingletonFreeImplementation@2]
    version = 1
}

ScoreReq.CompReq IClientConnectionGetStateAPI {
    description = "`IClientConnection` shall provide a `GetState` method that returns the current connection state."
    safety = ScoreReq.Asil.B
    derived_from = [MessagePassing.ClientInterface@1]
    version = 2
}

ScoreReq.CompReq IClientConnectionGetStopReasonAPI {
    description = "`IClientConnection` shall provide a `GetStopReason` method that returns the reason for the most recent transition to the `Stopping`/`Stopped` state."
    safety = ScoreReq.Asil.B
    derived_from = [MessagePassing.ClientInterface@1]
    version = 2
}

ScoreReq.CompReq IClientConnectionStartAPI {
    description = "`IClientConnection` shall provide a `Start` method that begins connecting to the server, registering the state and notification callbacks for the connection's lifetime."
    safety = ScoreReq.Asil.B
    derived_from = [MessagePassing.ClientInterface@1]
    version = 2
}

ScoreReq.CompReq IClientConnectionStopAPI {
    description = "`IClientConnection` shall provide a `Stop` method that ends the existing connection."
    safety = ScoreReq.Asil.B
    derived_from = [MessagePassing.ClientInterface@1]
    version = 2
}

ScoreReq.CompReq IClientConnectionRestartAPI {
    description = "`IClientConnection` shall provide a `Restart` method that attempts to bring a stopped connection back to the `Starting` state."
    safety = ScoreReq.Asil.B
    derived_from = [MessagePassing.ClientInterface@1]
    version = 2
}

ScoreReq.CompReq IServerConnectionGetClientIdentityAPI {
    description = "`IServerConnection` shall provide a `GetClientIdentity` method that returns the client's OS-provided process ID (PID), user ID (UID), and primary group ID (GID), established once when the connection was accepted."
    note = "A PID identifies a client process uniquely only among processes running simultaneously; the OS may reuse a PID for a different process afterwards, so it shall not be used by itself as a persistent, long-term client identity. A UID identifies a client process uniquely only if the integrating system dedicates a UID to that client process. The UID and/or the primary GID may be used by the server-side application for access control decisions. On QNX, this data is only meaningful when the connection uses the QNX-native-messaging transport (see SafetyCertifiedTransportMechanismUnderQNX); the Unix Domain Sockets backend on QNX, used there for internal testing purposes only, cannot retrieve real peer credentials and reports pid=uid=gid=0 instead."
    safety = ScoreReq.Asil.B
    derived_from = [MessagePassing.ClientIdentificationForAccessControl@2]
    version = 1
}

ScoreReq.CompReq IServerConnectionGetUserDataAPI {
    description = "`IServerConnection` shall provide a `GetUserData` method that returns the `UserData` object associated with the connection, as returned by the connection callback when the connection was accepted."
    safety = ScoreReq.Asil.B
    derived_from = [MessagePassing.ServerInterface@2]
    version = 1
}

}

section "Server Unit Requirements" {

ScoreReq.CompReq ServerPreallocatesConnectionObjects {
    description = "The server shall preallocate memory for the number of `IServerConnection` objects specified by `ServerConfig::pre_alloc_connections` at construction time, without allocating additional memory for each incoming client connection."
    safety = ScoreReq.Asil.B
    derived_from = [MessagePassing.AllowsBoundedMonotonicMemoryAllocation@2]
    version = 1
}

ScoreReq.CompReq ServerRingBufferQueueSizeConfigurable {
    description = "The server shall implement the shared incoming message queue as a ring buffer with the number of slots equal to `ServerConfig::max_queued_sends`, configured at construction time."
    safety = ScoreReq.Asil.B
    derived_from = [MessagePassing.AllowsBoundedMonotonicMemoryAllocation@2]
    version = 1
}

ScoreReq.CompReq ServerConnectionRefusal {
    description = "The server shall enable the connection callback to reject an incoming client connection by returning an error, without establishing a server connection for the rejected client."
    safety = ScoreReq.Asil.B
    derived_from = [MessagePassing.ServerInterface@2]
    version = 1
}

ScoreReq.CompReq ServerIConnectionHandlerDispatch {
    description = "The server shall invoke the `IConnectionHandler` virtual methods of the `UserData` object for a given `IServerConnection` instead of the server-wide callbacks, when the UserData holds an `IConnectionHandler` instance."
    safety = ScoreReq.Asil.B
    derived_from = [MessagePassing.ServerInterface@2]
    version = 1
}

}

section "Client Unit Requirements (client_connection)" {

ScoreReq.CompReq ClientConnectionSendQueuePreallocation {
    description = "The `ClientConnection` shall preallocate send queue storage for the number of asynchronous messages specified by `ClientConfig::max_queued_sends` at construction time."
    note = "This requirement is intended to ensure a design that avoids dynamic memory allocation for the send queue, after the construction."
    safety = ScoreReq.Asil.B
    derived_from = [MessagePassing.AllowsBoundedMonotonicMemoryAllocation@2]
    version = 1
}

ScoreReq.CompReq ClientConnectionSharedResourceEngineInjection {
    description = "The `ClientConnection` shall accept an `ISharedResourceEngine` instance as a constructor parameter, which shouldbe the exclusive provider forall shared resources."
    safety = ScoreReq.Asil.B
    derived_from = [MessagePassing.SingletonFreeImplementation@2]
    version = 1
}

ScoreReq.CompReq ClientConnectionMockInjectionForTesting {
    description = "The `ClientConnection` shall use the `ISharedResourceEngine` interface for all OS interactions."
    note="This enables injection of mock implementations for unit testing."
    safety = ScoreReq.Asil.B
    derived_from = [MessagePassing.AllowsResourceMockInjectionForTesting@2]
    version = 1
}

ScoreReq.CompReq ClientConnectionSendFailsWhenStopped {
    description = "The `ClientConnection` shall return an error for a Send call when the connection is in the `Stopped` state."
    safety = ScoreReq.Asil.B
    derived_from = [MessagePassing.SynchronousUnidirectionalCommunication@3]
    version = 1
}

ScoreReq.CompReq ClientConnectionSendWaitReplyFailsWhenStopped {
    description = "The `ClientConnection` shall return an error for a `SendWaitReply` call when the connection is in the `Stopped` state."
    safety = ScoreReq.Asil.B
    derived_from = [MessagePassing.SynchronousBidirectionalCommunication@2]
    version = 1
}

ScoreReq.CompReq ClientConnectionSendWithCallbackFailsWhenStopped {
    description = "The `ClientConnection` shall return an error for a `SendWithCallback` call when the connection is in the `Stopped` state."
    safety = ScoreReq.Asil.B
    derived_from = [MessagePassing.AsynchronousUnidirectionalCommunication@3]
    version = 1
}

ScoreReq.CompReq ClientConnectionStateCallbackInvocation {
    description = "The `ClientConnection` shall invoke the registered `StateCallback` each time the connection state changes, passing the new state as the argument."
    safety = ScoreReq.Asil.B
    derived_from = [MessagePassing.ClientInterface@1]
    version = 2
}

}
