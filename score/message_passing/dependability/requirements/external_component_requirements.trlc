/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package MessagePassing

import ScoreReq

// Not built: AoU candidate (subject is the OS transport); move to an assumptions_of_use target with the safety-analysis rewrite.
section "Requirements towards the system" {

ScoreReq.CompReq ConnectionIdentityIntegrityGuaranteed {
    description = "The transport mechanism shall ensure that the client identity established for a Server Connection cannot be forged by the client and remains valid for the entire lifetime of that Server Connection."
    note = "Replaces the retired UnforgableSenderIdentity record: the integrity guarantee covers the whole Server Connection lifetime, not just the message that established it."
    safety = ScoreReq.Asil.B
    derived_from = [MessagePassing.ServerInterface@2]
    version = 1
}

}
