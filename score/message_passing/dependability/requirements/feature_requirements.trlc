/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package MessagePassing

import ScoreReq

///////////////////////////////
// Feature Requirements
// Integration level requirements derived from Assumed System Requirements
///////////////////////////////

ScoreReq.FeatReq ServerInterface {
    description = "The message passing component shall provide a server interface that registers connection handlers and processes incoming requests."
    safety = ScoreReq.Asil.B
    derived_from = [MessagePassing.SystemMessagingProtocol@1]
    version = 1
}

ScoreReq.FeatReq OSIndependentAPI {
    description = "The message passing component shall provide an OS-independent API for OS-native IPC mechanisms."
    safety = ScoreReq.Asil.B
    derived_from = [MessagePassing.SystemMessagingProtocol@1]
    version = 1
}

ScoreReq.FeatReq SafetyCertifiedTransportMechanism {
    description = "The implementation under QNX shall use a safety-certified transport mechanism."
    safety = ScoreReq.Asil.B
    derived_from = [MessagePassing.SystemMessagingProtocol@1]
    version = 1
}

ScoreReq.FeatReq PointToPointConnections {
    description = "The message passing component shall support only point-to-point (1:1) connections between communication endpoints. N:M connections are explicitly excluded."
    safety = ScoreReq.Asil.B
    derived_from = [MessagePassing.SystemMessagingProtocol@1]
    version = 1
}

ScoreReq.FeatReq SmallDataLowLatencyCommunication {
    description = "The message passing component shall provide low-latency communication for small data between dedicated endpoints. "
    safety = ScoreReq.Asil.B
    derived_from = [MessagePassing.SystemMessagingProtocol@1]
    version = 1
}

ScoreReq.FeatReq SynchronousUnidirectionalCommunication {
    description = "The communication shall support synchronous unidirectional message sending on a given connection. The send call blocks until the message has been transferred to the receiving side and a suitable handler has been identified."
    safety = ScoreReq.Asil.B
    derived_from = [MessagePassing.SystemMessagingProtocol@1]
    version = 1
}

ScoreReq.FeatReq SynchronousBidirectionalCommunication {
    description = "The communication shall support synchronous bidirectional request-response communication on a given connection. The send call blocks until a reply from the receiver has been received (SendWaitReply)."
    safety = ScoreReq.Asil.B
    derived_from = [MessagePassing.SystemMessagingProtocol@1]
    version = 1
}

ScoreReq.FeatReq AsynchronousUnidirectionalCommunication {
    description = "The communication shall support asynchronous unidirectional message sending, where the send call returns after the local message passing layer has accepted the message. No guarantee is provided that the message is delivered to or processed by the receiver."
    safety = ScoreReq.Asil.B
    derived_from = [MessagePassing.SystemMessagingProtocol@1]
    version = 1
}

ScoreReq.FeatReq SingletonFreeImplementation {
    description = "The Message Passing library design shall not use any singletons."
    note = "Since resource management and life-cycle of the singleton are hard to track."
    safety = ScoreReq.Asil.B
    derived_from = [MessagePassing.SystemMessagingProtocol@1]
    version = 1
}

ScoreReq.FeatReq AllowsBoundedMonotonicMemoryAllocation {
    description = "The Message Passing library design shall allow bounded monotonic memory allocation."
    safety = ScoreReq.Asil.B
    derived_from = [MessagePassing.SystemMessagingProtocol@1]
    version = 1
}

ScoreReq.FeatReq AllowsResourceMockInjectionForTesting {
    description = "The Message Passing library design shall allow resource mock injection for testing."
    safety = ScoreReq.Asil.B
    derived_from = [MessagePassing.SystemMessagingProtocol@1]
    version = 1
}
