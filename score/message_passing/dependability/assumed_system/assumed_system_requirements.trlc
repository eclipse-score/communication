/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package MessagePassing

import ScoreReq

///////////////////////////////
// Assumed System Requirements
// System level requirements for MessagePassing SEooC
///////////////////////////////

ScoreReq.AssumedSystemReq SystemMessagingProtocol {
    description = "The system shall provide a mechanism for inter-process communication via a client-server messaging protocol."
    safety = ScoreReq.Asil.B
    rationale = "Application processes need to exchange requests and responses process boundaries, while adhearing to the failiure modes of ISO-26262."
    version = 1
}

ScoreReq.AssumedSystemReq SafeState {
    description = "The Safe State of the system shall be *safe-silent*"
    safety = ScoreReq.Asil.B
    rationale = "Currently only fail safe systems are in scope"
    version = 1
}
