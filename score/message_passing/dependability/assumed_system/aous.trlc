/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package MessagePassing

import ScoreReq

// TODO: Add Assumptions of Use (AoU) for message passing
// Example:

ScoreReq.AoU ExampleAoU {
    description = "Example assumption description"
    safety = ScoreReq.Asil.B
    note = "Example note"
    version = 1
}
