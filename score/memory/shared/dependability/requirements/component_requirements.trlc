/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package MemoryShared

import ScoreReq

ScoreReq.CompReq CreateFailsIfObjectAlreadyExists {
    description = """When creating a shared memory object, the shared memory library shall not provide an object and leave the existing object untouched
    if an object with the same name already exists or its creation lock cannot be acquired."""
    safety = ScoreReq.Asil.B
    derived_from = [MemoryShared.FEAT_CreateSharedMemoryObject@1, MemoryShared.FEAT_ConcurrentCreateOrOpen@1, MemoryShared.FEAT_NoResultOnFailure@1]
    version = 1
}

ScoreReq.CompReq OpenFailsIfObjectCannotBeOpened {
    description = """When opening a shared memory object with Open and the operating system refuses to open it, for example because it does not exist
    or the caller lacks the required access rights, the shared memory library shall not provide an object."""
    safety = ScoreReq.Asil.B
    derived_from = [MemoryShared.FEAT_OpenSharedMemoryObject@1, MemoryShared.FEAT_NoResultOnFailure@1]
    version = 1
}

ScoreReq.CompReq OpenMapsObjectWithItsActualSize {
    description = """When opening an existing shared memory object, the shared memory library shall map it with the size
    reported by the operating system for that object."""
    safety = ScoreReq.Asil.B
    derived_from = [MemoryShared.FEAT_OpenSharedMemoryObject@1]
    version = 1
}

ScoreReq.CompReq RemoveDeletesNameOnly {
    description = """When Remove is called for a shared memory object that is opened in the calling process, the shared memory library
    shall delete its name so that it can no longer be opened, while existing mappings of the object remain valid."""
    safety = ScoreReq.Asil.B
    derived_from = [MemoryShared.FEAT_RemoveSharedMemoryObject@1]
    version = 1
}

ScoreReq.CompReq RemoveStaleArtefactsDeletesLockFileAndName {
    description = """When RemoveStaleArtefacts is called for a shared memory object that is not opened in the calling process, the shared memory library
    shall delete its creation lock file and its name, using the typed memory provider for an object in typed memory."""
    safety = ScoreReq.Asil.B
    derived_from = [MemoryShared.FEAT_RemoveSharedMemoryObject@1]
    version = 1
}

ScoreReq.CompReq TerminateIfStaleArtefactsOfOpenedObjectAreRemoved {
    description = """The shared memory library shall terminate the process if RemoveStaleArtefacts is called for a shared memory object
    that is opened in the calling process."""
    safety = ScoreReq.Asil.B
    derived_from = [MemoryShared.FEAT_RemoveSharedMemoryObject@1, MemoryShared.FEAT_SafeSilentOnUnrecoverableError@1]
    version = 1
}

ScoreReq.CompReq CreateOrOpenFallsBackToOpen {
    description = """When CreateOrOpen does not find the shared memory object, the shared memory library shall try to create it,
    and if creation fails because the object already exists or its creation lock cannot be acquired, it shall open the object."""
    safety = ScoreReq.Asil.B
    derived_from = [MemoryShared.FEAT_ConcurrentCreateOrOpen@1]
    version = 1
}

ScoreReq.CompReq ReuseAlreadyOpenedObject {
    description = """When Open or CreateOrOpen is called for a shared memory object that is already opened in the calling process,
    the shared memory library shall provide the already opened object, with the access it was first opened with, without mapping it again."""
    safety = ScoreReq.Asil.B
    derived_from = [MemoryShared.FEAT_SingleMappingPerProcess@1]
    version = 1
}

ScoreReq.CompReq NoFixedMappingAddress {
    description = "The shared memory library shall let the operating system choose the virtual address at which a shared memory object is mapped."
    safety = ScoreReq.Asil.B
    derived_from = [MemoryShared.FEAT_CreateSharedMemoryObject@1, MemoryShared.FEAT_OpenSharedMemoryObject@1]
    version = 1
}

ScoreReq.CompReq OffsetPtrIsRelative {
    description = """The shared memory library shall provide an OffsetPtr that stores the distance between its own address and its target, so that it refers
    to the same target at any address at which the shared memory object is mapped."""
    safety = ScoreReq.Asil.B
    derived_from = [MemoryShared.FEAT_BoundsCheckedPointers@1]
    version = 1
}

ScoreReq.CompReq AllocateWithinObject {
    description = "The shared memory library shall return memory allocated from a shared memory object only from within the usable region of that object."
    safety = ScoreReq.Asil.B
    derived_from = [MemoryShared.FEAT_AllocationWithinSharedMemoryObject@1, MemoryShared.FEAT_FixedObjectSize@1]
    version = 1
}

ScoreReq.CompReq AlignedAllocation {
    description = "The shared memory library shall return memory allocated from a shared memory object aligned to the requested alignment."
    safety = ScoreReq.Asil.B
    derived_from = [MemoryShared.FEAT_AllocationWithinSharedMemoryObject@1]
    version = 1
}

ScoreReq.CompReq AllocatorReturnsOffsetPtr {
    description = """The PolymorphicOffsetPtrAllocator shall allocate memory from the memory resource it was constructed with
    and return the allocated memory as an OffsetPtr."""
    safety = ScoreReq.Asil.B
    derived_from = [MemoryShared.FEAT_AllocationWithinSharedMemoryObject@1, MemoryShared.FEAT_BoundsCheckedPointers@1]
    version = 1
}

ScoreReq.CompReq ContainersAllocateViaOffsetPtrAllocator {
    description = """The shared memory library shall provide the container types Vector and Map, which allocate their elements, including the elements
    of nested Vector and Map instances, via the PolymorphicOffsetPtrAllocator from the memory resource they are constructed with."""
    safety = ScoreReq.Asil.B
    derived_from = [MemoryShared.FEAT_AllocationWithinSharedMemoryObject@1, MemoryShared.FEAT_BoundsCheckedPointers@1]
    version = 1
}

ScoreReq.CompReq ApplyRequestedPermissionsOnCreation {
    description = """When creating a shared memory object in system memory with a list of user permissions, the shared memory library shall grant read and write access
    to the creator and grant every listed user only the read or write access listed for that user."""
    safety = ScoreReq.Asil.B
    derived_from = [MemoryShared.FEAT_AccessRightsOnCreation@1]
    version = 1
}

ScoreReq.CompReq ApplyWorldReadablePermissionsOnCreation {
    description = """When creating a shared memory object in system memory with world-readable permissions, the shared memory library shall grant read and write access
    to the creator and read-only access to all other users."""
    safety = ScoreReq.Asil.B
    derived_from = [MemoryShared.FEAT_AccessRightsOnCreation@1]
    version = 1
}

ScoreReq.CompReq ApplyWorldWritablePermissionsOnCreation {
    description = """When creating a shared memory object in system memory with world-writable permissions, the shared memory library shall grant read and write access
    to the creator and to all other users."""
    safety = ScoreReq.Asil.B
    derived_from = [MemoryShared.FEAT_AccessRightsOnCreation@1]
    version = 1
}

ScoreReq.CompReq PassPermissionsToTypedMemoryProvider {
    description = """When creating a shared memory object in typed memory, the shared memory library shall pass the requested permissions
    to the typed memory provider instead of applying them itself."""
    safety = ScoreReq.Asil.B
    derived_from = [MemoryShared.FEAT_AccessRightsOnCreation@1]
    version = 1
}

ScoreReq.CompReq OpenReadOnly {
    description = """When opening a shared memory object that is not yet opened in the calling process with Open for read-only access,
    the shared memory library shall open and map the object with read access only."""
    safety = ScoreReq.Asil.B
    derived_from = [MemoryShared.FEAT_AccessModeOnOpening@1]
    version = 1
}

ScoreReq.CompReq OpenReadWrite {
    description = """When opening a shared memory object that is not yet opened in the calling process with Open for read-write access,
    the shared memory library shall open and map the object with read and write access."""
    safety = ScoreReq.Asil.B
    derived_from = [MemoryShared.FEAT_AccessModeOnOpening@1]
    version = 1
}

ScoreReq.CompReq CreatorMapsReadWrite {
    description = """When Create or CreateOrOpen is called for a shared memory object that is not yet opened in the calling process,
    the shared memory library shall open and map the object with read and write access."""
    safety = ScoreReq.Asil.B
    derived_from = [MemoryShared.FEAT_CreateSharedMemoryObject@1, MemoryShared.FEAT_ConcurrentCreateOrOpen@1]
    version = 1
}

ScoreReq.CompReq RejectObjectOfUnexpectedCreator {
    description = """When a list of expected creators is given on opening a shared memory object (Open, or CreateOrOpen of an existing object),
    the shared memory library shall not provide the object if its creator is neither the calling user nor contained in that list."""
    safety = ScoreReq.Asil.B
    derived_from = [MemoryShared.FEAT_CreatorVerification@1, MemoryShared.FEAT_NoResultOnFailure@1]
    version = 1
}

ScoreReq.CompReq DetermineCreatorFromObjectOwner {
    description = "The shared memory library shall take the owner user ID reported by the operating system for a shared memory object as the user ID of its creator."
    safety = ScoreReq.Asil.B
    derived_from = [MemoryShared.FEAT_CreatorVerification@1]
    version = 1
}

ScoreReq.CompReq DetermineCreatorOfTypedMemoryObjectViaProvider {
    description = "For a shared memory object owned by the typed memory daemon, the shared memory library shall determine its creator via the typed memory provider."
    safety = ScoreReq.Asil.B
    derived_from = [MemoryShared.FEAT_CreatorVerification@1]
    version = 1
}

ScoreReq.CompReq TerminateIfSizeOrCreatorCannotBeDetermined {
    description = """The shared memory library shall terminate the process if the size or the creator of a shared memory object being opened
    cannot be determined."""
    safety = ScoreReq.Asil.B
    derived_from = [MemoryShared.FEAT_CreatorVerification@1, MemoryShared.FEAT_OpenSharedMemoryObject@1, MemoryShared.FEAT_SafeSilentOnUnrecoverableError@1]
    version = 1
}

ScoreReq.CompReq OffsetPtrChecksTargetWithinObject {
    description = """When the target of an OffsetPtr located in a shared memory object is accessed or obtained as a raw pointer while bounds checking
    is enabled, the shared memory library shall check that the complete pointed-to object, from its first to its last byte, lies within that shared memory object."""
    safety = ScoreReq.Asil.B
    derived_from = [MemoryShared.FEAT_BoundsCheckedPointers@1]
    version = 1
}

ScoreReq.CompReq OffsetPtrCopyKeepsBounds {
    description = """When an OffsetPtr is copied by copy construction or copy assignment from a shared memory object to memory outside any shared memory object
    while bounds checking is enabled, the shared memory library shall keep the bounds of the source shared memory object in the copy and in all further copies
    made from it by copy construction or copy assignment, and shall check every access to the target of such a copy, or every raw pointer obtained from it,
    against these bounds."""
    safety = ScoreReq.Asil.B
    derived_from = [MemoryShared.FEAT_BoundsCheckedPointers@1]
    version = 1
}

ScoreReq.CompReq OffsetRefChecksTargetWithinObject {
    description = """When an OffsetRef located in a shared memory object is accessed while bounds checking is enabled, the shared memory library shall check
    that the complete referenced object, from its first to its last byte, lies within that shared memory object."""
    safety = ScoreReq.Asil.B
    derived_from = [MemoryShared.FEAT_BoundsCheckedPointers@1]
    version = 1
}

ScoreReq.CompReq OverflowSafeTargetCalculation {
    description = """The shared memory library shall treat a target address calculation from an offset stored in a shared memory object
    that overflows the address range as a failed bounds check."""
    safety = ScoreReq.Asil.B
    derived_from = [MemoryShared.FEAT_BoundsCheckedPointers@1]
    version = 1
}

ScoreReq.CompReq MemoryResourceProxyWithinItsResource {
    description = """When allocating via a MemoryResourceProxy while bounds checking is enabled, the shared memory library shall check that the proxy refers
    to a known memory resource and that the start address of the proxy lies within the memory of that memory resource."""
    safety = ScoreReq.Asil.B
    derived_from = [MemoryShared.FEAT_AllocationWithinSharedMemoryObject@1]
    version = 1
}

ScoreReq.CompReq ObjectBoundsFromLocalMapping {
    description = """The shared memory library shall use the address at which a shared memory object is mapped in the calling process and the mapped size
    as the bounds of that object."""
    safety = ScoreReq.Asil.B
    derived_from = [MemoryShared.FEAT_BoundsCheckedPointers@1, MemoryShared.FEAT_AllocationWithinSharedMemoryObject@1]
    version = 1
}

ScoreReq.CompReq TerminateOnBoundsViolation {
    description = "The shared memory library shall terminate the process if a bounds check fails."
    safety = ScoreReq.Asil.B
    derived_from = [MemoryShared.FEAT_BoundsCheckedPointers@1, MemoryShared.FEAT_AllocationWithinSharedMemoryObject@1, MemoryShared.FEAT_SafeSilentOnUnrecoverableError@1]
    version = 1
}

ScoreReq.CompReq BoundsCheckingEnabledByDefault {
    description = "The shared memory library shall enable the bounds checks of OffsetPtr, OffsetRef and MemoryResourceProxy by default."
    safety = ScoreReq.Asil.B
    derived_from = [MemoryShared.FEAT_BoundsCheckedPointers@1, MemoryShared.FEAT_AllocationWithinSharedMemoryObject@1]
    version = 1
}

ScoreReq.CompReq TerminateOnUnexpectedCreationError {
    description = """The shared memory library shall terminate the process if creating a shared memory object fails for a reason other than
    an object with the same name already existing or its creation lock not being acquirable."""
    safety = ScoreReq.Asil.B
    derived_from = [MemoryShared.FEAT_SafeSilentOnUnrecoverableError@1]
    version = 1
}

ScoreReq.CompReq TerminateOnUnexpectedCreateOrOpenError {
    description = """The shared memory library shall terminate the process if CreateOrOpen fails to open a shared memory object
    for a reason other than the object not existing."""
    safety = ScoreReq.Asil.B
    derived_from = [MemoryShared.FEAT_SafeSilentOnUnrecoverableError@1]
    version = 1
}

ScoreReq.CompReq TerminateIfObjectSizeCannotBeSet {
    description = "The shared memory library shall terminate the process if setting the size of a shared memory object being created fails."
    safety = ScoreReq.Asil.B
    derived_from = [MemoryShared.FEAT_SafeSilentOnUnrecoverableError@1]
    version = 1
}

ScoreReq.CompReq TerminateIfObjectCannotBeMapped {
    description = "The shared memory library shall terminate the process if mapping a shared memory object into the calling process fails."
    safety = ScoreReq.Asil.B
    derived_from = [MemoryShared.FEAT_SafeSilentOnUnrecoverableError@1]
    version = 1
}

ScoreReq.CompReq TerminateIfObjectBoundsCannotBeRegistered {
    description = "The shared memory library shall terminate the process if the bounds of a mapped shared memory object cannot be registered."
    safety = ScoreReq.Asil.B
    derived_from = [MemoryShared.FEAT_SafeSilentOnUnrecoverableError@1]
    version = 1
}

ScoreReq.CompReq TerminateIfAllocationDoesNotFit {
    description = """The shared memory library shall terminate the process if a requested allocation does not fit into the remaining usable region
    of the shared memory object."""
    safety = ScoreReq.Asil.B
    derived_from = [MemoryShared.FEAT_SafeSilentOnUnrecoverableError@1, MemoryShared.FEAT_FixedObjectSize@1]
    version = 1
}

ScoreReq.CompReq InitializeBeforeCreateReturns {
    description = """When creating a shared memory object, the shared memory library shall initialize its own management data in the object
    and then call the initialization callback given by the creator, before the creating call returns."""
    safety = ScoreReq.Asil.B
    derived_from = [MemoryShared.FEAT_InitializationOnCreation@1]
    version = 1
}

ScoreReq.CompReq CreatorHoldsCreationLock {
    description = """When creating a shared memory object, the shared memory library shall first acquire the creation lock of that name,
    which only one process can hold at a time, and shall release it only after the initialization callback has returned."""
    safety = ScoreReq.Asil.B
    derived_from = [MemoryShared.FEAT_OpenOnlyAfterInitialization@1]
    version = 1
}

ScoreReq.CompReq OpenHoldsCreationLock {
    description = """When opening a shared memory object with Open or CreateOrOpen, the shared memory library shall first acquire the creation lock
    of that name, waiting while another process holds it, and shall release the lock only after the object has been opened and mapped."""
    safety = ScoreReq.Asil.B
    derived_from = [MemoryShared.FEAT_OpenOnlyAfterInitialization@1]
    version = 1
}

ScoreReq.CompReq TerminateIfCreationLockIsNotReleased {
    description = """The shared memory library shall terminate the process if the creation lock of a shared memory object being opened
    is not released within a fixed timeout."""
    safety = ScoreReq.Asil.B
    derived_from = [MemoryShared.FEAT_OpenOnlyAfterInitialization@1, MemoryShared.FEAT_SafeSilentOnUnrecoverableError@1]
    version = 1
}

ScoreReq.CompReq LockFileCreateIsExclusive {
    description = """When creating a lock file with LockFile::Create, the shared memory library shall create the file exclusively,
    so that creation fails if a file with the same path already exists."""
    safety = ScoreReq.Asil.B
    derived_from = [MemoryShared.FEAT_OpenOnlyAfterInitialization@1, MemoryShared.FEAT_InterProcessLock@1]
    version = 1
}

ScoreReq.CompReq LockFileFailureProvidesNoLockFile {
    description = """If the file of a lock file cannot be created or opened, or its access rights cannot be set, the shared memory library
    shall not provide a LockFile."""
    safety = ScoreReq.Asil.B
    derived_from = [MemoryShared.FEAT_InterProcessLock@1, MemoryShared.FEAT_NoResultOnFailure@1]
    version = 1
}

ScoreReq.CompReq LockFileOwnerDeletesFileOnDestruction {
    description = """When a LockFile is destroyed, the shared memory library shall close its file and, if the LockFile owns the file, also delete it.
    A LockFile owns its file if it was created with LockFile::Create, with LockFile::CreateOrOpen requesting ownership, or after TakeOwnership was called;
    ownership moves with the LockFile on move construction and move assignment."""
    safety = ScoreReq.Asil.B
    derived_from = [MemoryShared.FEAT_OpenOnlyAfterInitialization@1, MemoryShared.FEAT_InterProcessLock@1]
    version = 1
}

ScoreReq.CompReq FlockMutexLockAndUnlock {
    description = """The shared memory library shall provide an exclusive and a shared inter-process mutex on a lock file, whose lock operation acquires
    an exclusive or shared file lock respectively, waiting until it can be acquired, and whose unlock operation releases it."""
    safety = ScoreReq.Asil.B
    derived_from = [MemoryShared.FEAT_InterProcessLock@1]
    version = 1
}

ScoreReq.CompReq FlockMutexTryLockWithoutWaiting {
    description = """When the try-lock operation of an inter-process mutex is called, the shared memory library shall try to acquire the file lock
    without waiting and shall report failure if another process holds a conflicting lock."""
    safety = ScoreReq.Asil.B
    derived_from = [MemoryShared.FEAT_InterProcessLock@1]
    version = 1
}

ScoreReq.CompReq TerminateOnUnexpectedFileLockError {
    description = """The shared memory library shall terminate the process if acquiring or releasing the file lock of an inter-process mutex fails
    for a reason other than the lock being held by another process."""
    safety = ScoreReq.Asil.B
    derived_from = [MemoryShared.FEAT_InterProcessLock@1, MemoryShared.FEAT_SafeSilentOnUnrecoverableError@1]
    version = 1
}

ScoreReq.CompReq TerminateAfterBoundedAllocationRetries {
    description = """The shared memory library shall terminate the process if an allocation from a shared memory object does not succeed
    within a fixed number of attempts to update the allocation position stored in the object."""
    safety = ScoreReq.Asil.B
    derived_from = [MemoryShared.FEAT_SafeSilentOnUnrecoverableError@1]
    version = 1
}

ScoreReq.CompReq AllocationCoordinatedByAtomicUpdate {
    description = """The shared memory library shall coordinate concurrent allocations from a shared memory object only through an atomic update
    of the allocation position stored in the object."""
    safety = ScoreReq.Asil.B
    derived_from = [MemoryShared.FEAT_AllocationWithinSharedMemoryObject@1]
    version = 1
}

ScoreReq.CompReq SizeSetOnlyOnCreation {
    description = "The shared memory library shall set the size of a shared memory object only while creating it."
    safety = ScoreReq.Asil.B
    derived_from = [MemoryShared.FEAT_FixedObjectSize@1]
    version = 1
}

ScoreReq.CompReq UsableRegionOfRequestedSize {
    description = """When creating a shared memory object, the shared memory library shall provide a usable region of exactly the requested size,
    in addition to the space it needs for its own management data."""
    safety = ScoreReq.Asil.B
    derived_from = [MemoryShared.FEAT_CreateSharedMemoryObject@1]
    version = 1
}
