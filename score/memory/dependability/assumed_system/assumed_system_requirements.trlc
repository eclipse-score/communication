/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package ScoreMemory

import ScoreReq

///////////////////////////////
// Assumed System Requirements
// System level requirements for ScoreMemory SEooC
///////////////////////////////

ScoreReq.AssumedSystemReq SharedMemoryIPC {
    description = "The system shall provide a mechanism for inter-process shared memory that allows multiple processes to exchange data through a common memory region, compliant with the selected :term:`integrity level`."
    safety = ScoreReq.Asil.B
    rationale = "Middleware components (e.g. ara::com) require a shared memory abstraction to enable zero-copy inter-process communication while satisfying ISO-26262 safety requirements."
    version = 1
}

ScoreReq.Mitigation SafeState {
    description = "The Safe State of the system shall be *safe-silent*."
    safety = ScoreReq.Asil.B
    rationale = "Only fail-safe systems are in scope; on unrecoverable error the component shall stop producing output."
    version = 1
}
