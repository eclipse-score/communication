/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package SomeipSdDaemon

import ScoreReq

ScoreReq.CompReq CR_SdDaemon_DaemonApplication {
    description = "The sd daemon shall run as a daemon process."
    safety = ScoreReq.Asil.QM
    derived_from = [ SomeipSdDaemon.FEAT_SdDaemonService@1 ]
    version = 1
}
