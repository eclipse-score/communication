/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package SampleType

import ScoreReq

ScoreReq.AoU SampleAoU {
    description = "It shall be made sure that this SampleAoU never ends up anywhere"
    safety = ScoreReq.Asil.B
    mitigates = "ShmemCreatedWrongName"
    version = 1
}
