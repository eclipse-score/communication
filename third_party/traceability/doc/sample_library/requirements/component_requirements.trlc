/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package SampleLibrary

import ScoreReq
import Communication

ScoreReq.CompReq SampleRequirement {
    description = "Description of our SampleRequirement"
    safety = ScoreReq.Asil.B
    derived_from = [Communication.SupportForTimeBasedArchitecture@2]
    version = 1
    fulfilledBy = "SampleLibrary"
}
